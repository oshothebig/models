/*
 * This module has been generated by smidump 0.4.8:
 *
 *      smidump -f yang BRIDGE-MIB
 *
 * Modify to make easier for REST API
 */

module BRIDGE-MIB {

  /*** NAMESPACE / PREFIX DEFINITION ***/

  namespace "urn:ietf:params:xml:ns:yang:smiv2:BRIDGE-MIB";
  prefix "bridge-mib";

  /*** LINKAGE (IMPORTS / INCLUDES) ***/

  import IF-MIB     { prefix "if-mib"; }
  import ieee-types { prefix "ieee"; }
  import ietf-yang-types { prefix "yang"; }

  /*** META INFORMATION ***/

  organization      
   "Snaproute";

  contact           
   "Email: ccordes@snaproute.com";

  description       
   "The Bridge MIB module for managing devices that support
    IEEE 802.1D.
    
    Copyright (C) The Internet Society (2005).  This version of
    this MIB module is part of RFC 4188; see the RFC itself for
    full legal notices.";

  revision "2005-09-19" {
    description     
     "Third revision, published as part of RFC 4188.
      
      The MIB module has been converted to SMIv2 format.
      Conformance statements have been added and some
      description and reference clauses have been updated.
      
      The object PortPathCost32 was added to
      support IEEE 802.1t and the permissible values of
      Priority and PortPriority have been
      clarified for bridges supporting IEEE 802.1t or
      IEEE 802.1w.
      
      The interpretation of TimeSinceTopologyChange
      has been clarified for bridges supporting the Rapid
      Spanning Tree Protocol (RSTP).";
  }
  revision "1993-07-31" {
    description     
     "Second revision, published as part of RFC 1493.";
  }
  revision "1991-12-31" {
    description     
     "Initial revision, published as part of RFC 1286.";
  }

  /*** TYPE DEFINITIONS ***/

  typedef BridgeId {
    type binary {
      length "8";
    }
    description     
     "The Bridge-Identifier, as used in the Spanning Tree
      Protocol, to uniquely identify a bridge.  Its first two
      octets in network byte order contain a priority value,
      and its last 6 octets contain the MAC address used to
      refer to a bridge in a unique fashion (typically, the
      numerically smallest MAC address of all ports on the
      bridge).";
  }

  typedef Timeout {
    type int32;
    description     
     "A Spanning Tree Protocol (STP) timer in units of 1/100
      seconds.  Several objects in this MIB module represent
      values of timers used by the Spanning Tree Protocol.
      In this MIB, these timers have values in units of
      hundredths of a second (i.e., 1/100 secs).
      
      These timers, when stored in a Spanning Tree Protocol's
      BPDU, are in units of 1/256 seconds.  Note, however, that
      802.1D-1998 specifies a settable granularity of no more
      than one second for these timers.  To avoid ambiguity,
      a conversion algorithm is defined below for converting
      between the different units, which ensures a timer's
      value is not distorted by multiple conversions.
      
      To convert a Timeout value into a value in units of
      1/256 seconds, the following algorithm should be used:
      
          b = floor( (n * 256) / 100)
      
      where:
          floor   =  quotient [ignore remainder]
          n is the value in 1/100 second units
          b is the value in 1/256 second units
      
      To convert the value from 1/256 second units back to
      1/100 seconds, the following algorithm should be used:
      
          n = ceiling( (b * 100) / 256)
      
      where:
          ceiling = quotient [if remainder is 0], or
                    quotient + 1 [if remainder is nonzero]
          n is the value in 1/100 second units
      
      
      
          b is the value in 1/256 second units
      
      Note: it is important that the arithmetic operations are
      done in the order specified (i.e., multiply first,
      divide second).";
  }
	
  list  Stp {
	key "IfIndex BrgIfIndex";
      description   
       "A list of information maintained by every port about
        the Spanning Tree Protocol state for that port.";

	leaf IfIndex {
        type int32 {
          range "1..65535";
        }
        //config false;
        description 
         "The port number of the port for which this entry
          contains Spanning Tree Protocol management information.";
        reference   
         "IEEE 802.1D-1998: clause 14.8.2.1.2";
      }
	
	leaf BrgIfIndex {
     	type if-mib:InterfaceIndex;
      	config true;
         description 
       	 "The value of the instance of the ifIndex object,
        	  for the bridge corresponding to this port.";
      	}

	// Config
	container Port {
      	description
			"configuration data related to stp port";

		
		leaf Priority {
	        type int32 {
	          range "0..255";
	        }
	        config true;
	        default 128;
	        description 
	         "The value of the priority field that is contained in
	          the first in network byte order octet of the 2 octet
	          long Port ID.  The other octet of the Port ID is given
	          by the value of StpPort.
	          On bridges supporting IEEE 802.1t or IEEE 802.1w,
	          permissible values are 0-240, in steps of 16.";
	        reference   
	         "IEEE 802.1D-1998 clause 8.10.2, Table 8-4,
	          
	          
	          
	          IEEE 802.1t clause 8.10.2, Table 8-4, clause 14.3.";
	      }
		leaf Enable {
	        type enumeration {
	          enum enabled  { value 1; }
	          enum disabled { value 2; }
	        }
	        config true;
	        default disabled;
	        description 
	         "The enabled/disabled status of the port.";
	        reference   
	         "IEEE 802.1D-1998: clause 8.5.5.2";
	    }
		
	    leaf PathCost {
	        type int32 {
	          range "1..65535";
	        }
	        config true;
	        default 1;
	        description 
	         "The contribution of this port to the path cost of
	          paths towards the spanning tree root which include
	          this port.  802.1D-1998 recommends that the default
	          value of this parameter be in inverse proportion to
	          the speed of the attached LAN.
	          
	          New implementations should support PathCost32.
	          If the port path costs exceeds the maximum value of this
	          object then this object should report the maximum value,
	          namely 65535.  Applications should try to read the
	          PathCost32 object if this object reports
	          the maximum value.

		  Value of 1 will force node to auto discover the value
                  based on the ports capabilities.";
	        reference   
	         "IEEE 802.1D-1998: clause 8.5.5.3";
	      }

      	leaf PathCost32 {
	        type int32 {
	          range "1..200000000";
	        }
	        config true;
	        default 1;
	        description 
	         "The contribution of this port to the path cost of
	          paths towards the spanning tree root which include
	          this port.  802.1D-1998 recommends that the default
	          value of this parameter be in inverse proportion to
	          the speed of the attached LAN.
	          
	          This object replaces PathCost to support
	          IEEE 802.1t.
		  Value of 1 will force node to auto discover the value
                  based on the ports capabilities.";
	        reference   
	         "IEEE 802.1t clause 8.10.2, Table 8-5.";
	      }
	  } // end config


	  container PortState {
		description
			"status data related to stp port";

        leaf Priority {
	        type int32 {
	          range "0..255";
	        }
	        config false;
	        description
	         "The value of the priority field that is contained in
	          the first in network byte order octet of the 2 octet
	          long Port ID.  The other octet of the Port ID is given
	          by the value of StpPort.
	          On bridges supporting IEEE 802.1t or IEEE 802.1w,
	          permissible values are 0-240, in steps of 16.";
	        reference
	         "IEEE 802.1D-1998 clause 8.10.2, Table 8-4,



	          IEEE 802.1t clause 8.10.2, Table 8-4, clause 14.3.";
	      }
		leaf Enable {
	        type enumeration {
	          enum enabled  { value 1; }
	          enum disabled { value 2; }
	        }
	        config false;
	        default enabled;
	        description
	         "The enabled/disabled status of the port.";
	        reference
	         "IEEE 802.1D-1998: clause 8.5.5.2";
	    }

	    leaf PathCost {
	        type int32 {
	          range "1..65535";
	        }
	        config false;
	        description
	         "The contribution of this port to the path cost of
	          paths towards the spanning tree root which include
	          this port.  802.1D-1998 recommends that the default
	          value of this parameter be in inverse proportion to



	          the speed of the attached LAN.

	          New implementations should support PathCost32.
	          If the port path costs exceeds the maximum value of this
	          object then this object should report the maximum value,
	          namely 65535.  Applications should try to read the
	          PathCost32 object if this object reports
	          the maximum value.";
	        reference
	         "IEEE 802.1D-1998: clause 8.5.5.3";
	      }

      	leaf PathCost32 {
	        type int32 {
	          range "1..200000000";
	        }
	        config false;
	        description
	         "The contribution of this port to the path cost of
	          paths towards the spanning tree root which include
	          this port.  802.1D-1998 recommends that the default
	          value of this parameter be in inverse proportion to
	          the speed of the attached LAN.

	          This object replaces PathCost to support
	          IEEE 802.1t.";
	        reference
	         "IEEE 802.1t clause 8.10.2, Table 8-5.";
	      }

      	leaf State {
	        type enumeration {
	          enum disabled   { value 1; }
	          enum blocking   { value 2; }
	          enum listening  { value 3; }
	          enum learning   { value 4; }
	          enum forwarding { value 5; }
	          enum broken     { value 6; }
	        }
	        config false;
	        description 
	         "The port's current state, as defined by application of
	          the Spanning Tree Protocol.  This state controls what
	          action a port takes on reception of a frame.  If the
	          bridge has detected a port that is malfunctioning, it
	          will place that port into the broken(6) state.  For
	          ports that are disabled (see Enable), this
	          object will have a value of disabled(1).";
	        reference   
	         "IEEE 802.1D-1998: clause 8.5.5.2";
	    }
		
		leaf DesignatedRoot {
	        type bridge-mib:BridgeId;
	        config false;
	        description 
	         "The unique Bridge Identifier of the Bridge
	          recorded as the Root in the Configuration BPDUs
	          transmitted by the Designated Bridge for the
	          segment to which the port is attached.";
	        reference   
	         "IEEE 802.1D-1998: clause 8.5.5.4";
	    }
		
      	leaf DesignatedCost {
	        type int32;
	        config false;
	        description 
	         "The path cost of the Designated Port of the segment
	          connected to this port.  This value is compared to the
	          Root Path Cost field in received bridge PDUs.";
	        reference   
	         "IEEE 802.1D-1998: clause 8.5.5.5";
	      }
		leaf DesignatedBridge {
	        type bridge-mib:BridgeId;
	        config false;
	        description 
	         "The Bridge Identifier of the bridge that this
	          port considers to be the Designated Bridge for
	          this port's segment.";
	        reference   
	         "IEEE 802.1D-1998: clause 8.5.5.6";
	      }
      
      	leaf DesignatedPort {
	        type binary {
	          length "2";
	        }
	        config false;
	        description 
	         "The Port Identifier of the port on the Designated
	          Bridge for this port's segment.";
	        reference   
	         "IEEE 802.1D-1998: clause 8.5.5.7";
	      }
		leaf ForwardTransitions {
	        type yang:counter32;
	        config false;
	        description 
	         "The number of times this port has transitioned
	          from the Learning state to the Forwarding state.";
	      }
		
	  } // end state

	}
list StpBridge {
	key "Vlan";
      description   
       "A list of information maintained by every port about
        the Spanning Tree Protocol state for that port.";
	
	leaf Vlan {
      type uint16 {
          range 1..4095;
      }
      config true;
      description
       "Each bridge is associated with a domain.  Typically this domain
	   is represented as the vlan; The default domain is typically 1";
      reference     
       "Cisco PVST+";
    }
	
  container Instance {
  
	leaf Address {
      type ieee:mac-address;
      config true;
      default "00:00:00:00:00:00";
      description   
       "The bridge identifier of the root of the spanning
        tree, as determined by the Spanning Tree Protocol,
        as executed by this node.  This value is used as
        the Root Identifier parameter in all Configuration
        Bridge PDUs originated by this node.  This is ";
      reference     
       "IEEE 802.1D-1998: clause 8.5.3.1";
    }
	

	leaf Priority {
      type int32 {
        range "0..65535";
      }
      config true;
      default 32768;
      description   
       "The value of the write-able portion of the Bridge ID
        i.e., the first two octets of the 8 octet long Bridge
        ID.  The other last 6 octets of the Bridge ID are
        given by the value of Address.
        On bridges supporting IEEE 802.1t or IEEE 802.1w,
        permissible values are 0-61440, in steps of 4096.  Extended
        Priority is enabled when the lower 12 bits are set using
        the Bridges VLAN id";
      reference     
       "IEEE 802.1D-1998 clause 8.10.2, Table 8-4,
        IEEE 802.1t clause 8.10.2, Table 8-4, clause 14.3.";
    }
	

    leaf MaxAge {
      type int32 {
        range "6..40";
      }
      units "seconds";
      config true;
      default 20;
      description   
       "The value that all bridges use for MaxAge when this
        bridge is acting as the root.  Note that 802.1D-1998
        specifies that the range for this parameter is related
        to the value of HelloTime.  The
        granularity of this timer is specified by 802.1D-1998 to
        be 1 second.  An agent may return a badValue error if a
        set is attempted to a value that is not a whole number
        of seconds.";
      reference     
       "IEEE 802.1D-1998: clause 8.5.3.8";
    }

    leaf HelloTime {
      type int32 {
        range "1..2";
      }
      units "seconds";
      config true;
      default 2;
      description   
       "The value that all bridges use for HelloTime when this
        bridge is acting as the root.  The granularity of this
        timer is specified by 802.1D-1998 to be 1 second.  An
        agent may return a badValue error if a set is attempted
        
        
        
        to a value that is not a whole number of seconds.";
      reference     
       "IEEE 802.1D-1998: clause 8.5.3.9";
    }

    leaf ForwardDelay {
      type int32 {
        range "3..30";
      }
      units "seconds";
      config true;
      default 15;
      description   
       "The value that all bridges use for ForwardDelay when
        this bridge is acting as the root.  Note that
        802.1D-1998 specifies that the range for this parameter
        is related to the value of MaxAge.  The
        granularity of this timer is specified by 802.1D-1998 to
        be 1 second.  An agent may return a badValue error if a
        set is attempted to a value that is not a whole number
        of seconds.";
      reference     
       "IEEE 802.1D-1998: clause 8.5.3.10";
    }
    leaf ForceVersion {
        type enumeration {
          enum stp        { value 1; }
          enum rstp-pvst  { value 2; }
          enum mstp       { value 3; }
        }
		config true;
		default rstp-pvst;
		description
		 "Stp Version";
    }
    leaf TxHoldCount {
		type int32 {
            range "1..10";
        }
        default 6;
	config true;
	description
        "Configures the number of BPDUs that can be sent before pausing for 1 second.";
    }
    /* XXX table comments here XXX */
  }

  container State {
	
	
	 leaf IfIndex {
       	 	type if-mib:InterfaceIndex;
        		config false;
	         description 
         	 "The value of the instance of the ifIndex object,
          	  for the bridge";
      }
	leaf Address {
      type ieee:mac-address;
      config false;
      description
       "The bridge identifier of the root of the spanning
        tree, as determined by the Spanning Tree Protocol,
        as executed by this node.  This value is used as
        the Root Identifier parameter in all Configuration
        Bridge PDUs originated by this node.";
      reference
       "IEEE 802.1D-1998: clause 8.5.3.1";
    }


	leaf Priority {
      type int32 {
        range "0..65535";
      }
      config false;
      description
       "The value of the write-able portion of the Bridge ID
        i.e., the first two octets of the 8 octet long Bridge
        ID.  The other last 6 octets of the Bridge ID are
        given by the value of Address.
        On bridges supporting IEEE 802.1t or IEEE 802.1w,
        permissible values are 0-61440, in steps of 4096.";
      reference
       "IEEE 802.1D-1998 clause 8.10.2, Table 8-4,
        IEEE 802.1t clause 8.10.2, Table 8-4, clause 14.3.";
    }

	  leaf ProtocolSpecification {
      type enumeration {
        enum unknown   { value 1; }
        enum decLb100  { value 2; }
        enum ieee8021d { value 3; }
      }
      config false;
      description   
       "An indication of what version of the Spanning Tree
        Protocol is being run.  The value 'decLb100(2)'
        indicates the DEC LANbridge 100 Spanning Tree protocol.
        IEEE 802.1D implementations will return 'ieee8021d(3)'.
        If future versions of the IEEE Spanning Tree Protocol
        that are incompatible with the current version
        are released a new value will be defined.";
    }
  leaf TimeSinceTopologyChange {
      type yang:timeticks;
      units "seconds";
      config false;
      description   
       "The time (in hundredths of a second) since the
        last time a topology change was detected by the
        bridge entity.
        For RSTP, this reports the time since the tcWhile
        timer for any port on this Bridge was nonzero.";
      reference     
       "IEEE 802.1D-1998 clause 14.8.1.1.,
        IEEE 802.1w clause 14.8.1.1.";
    }

    leaf TopChanges {
      type yang:counter32;
      config false;
      description   
       "The total number of topology changes detected by
        this bridge since the management entity was last
        reset or initialized.";
      reference     
       "IEEE 802.1D-1998 clause 14.8.1.1.";
    }

    leaf DesignatedRoot {
      type bridge-mib:BridgeId;
      config false;
      description   
       "The bridge identifier of the root of the spanning
        tree, as determined by the Spanning Tree Protocol,
        as executed by this node.  This value is used as
        the Root Identifier parameter in all Configuration
        Bridge PDUs originated by this node.";
      reference     
       "IEEE 802.1D-1998: clause 8.5.3.1";
    }

    leaf RootCost {
      type int32;
      config false;
      description   
       "The cost of the path to the root as seen from
        this bridge.";
      reference     
       "IEEE 802.1D-1998: clause 8.5.3.2";
    }

    leaf RootPort {
      type int32;
      config false;
      description   
       "The port number of the port that offers the lowest
        cost path from this bridge to the root bridge.";
      reference     
       "IEEE 802.1D-1998: clause 8.5.3.3";
    }

    leaf MaxAge {
      type int32;
      units "seconds";
      config false;
      description   
       "The maximum age of Spanning Tree Protocol information
        learned from the network on any port before it is
        discarded, in units of hundredths of a second.  This is
        the actual value that this bridge is currently using.";
      reference     
       "IEEE 802.1D-1998: clause 8.5.3.4";
    }

    leaf HelloTime {
      type int32;
      units "seconds";
      config false;
      description   
       "The amount of time between the transmission of
        Configuration bridge PDUs by this node on any port when
        it is the root of the spanning tree, or trying to become
        so, in units of hundredths of a second.  This is the
        actual value that this bridge is currently using.";
      reference     
       "IEEE 802.1D-1998: clause 8.5.3.5";
    }

    leaf HoldTime {
      type int32;
      units "seconds";
      config false;
      description   
       "This time value determines the interval length
        during which no more than two Configuration bridge
        PDUs shall be transmitted by this node, in units
        of hundredths of a second.";
      reference     
       "IEEE 802.1D-1998: clause 8.5.3.14";
    }

    leaf ForwardDelay {
      type int32;
      units "seconds";
      config false;
      description   
       "This time value, measured in units of hundredths of a
        second, controls how fast a port changes its spanning
        state when moving towards the Forwarding state.  The
        value determines how long the port stays in each of the
        Listening and Learning states, which precede the
        Forwarding state.  This value is also used when a
        topology change has been detected and is underway, to
        age all dynamic entries in the Forwarding Database.
        [Note that this value is the one that this bridge is
        currently using, in contrast to
        ForwardDelay, which is the value that this
        bridge and all others would start using if/when this
        bridge were to become the root.]";
      reference     
       "IEEE 802.1D-1998: clause 8.5.3.6";
    }
    leaf BridgeMaxAge {
      type int32;
      units "seconds";
      config false;
      description
       "The maximum age of Spanning Tree Protocol information
        learned from the network on any port before it is
        discarded, in units of hundredths of a second.  This is
        the provisioned value of the local bridge.";
      reference
       "IEEE 802.1D-1998: clause 8.5.3.4";
    }

    leaf BridgeHelloTime {
      type int32;
      units "seconds";
      config false;
      description
       "The amount of time between the transmission of
        Configuration bridge PDUs by this node on any port when
        it is the root of the spanning tree, or trying to become
        so, in units of hundredths of a second.  This is
        the provisioned value of the local bridge   .";
      reference
       "IEEE 802.1D-1998: clause 8.5.3.5";
    }

    leaf BridgeHoldTime {
      type int32;
      units "seconds";
      config false;
      description
       "This time value determines the interval length
        during which no more than two Configuration bridge
        PDUs shall be transmitted by this node, in units
        of hundredths of a second. This is
        the provisioned value of the local bridge";
      reference
       "IEEE 802.1D-1998: clause 8.5.3.14";
    }

    leaf BridgeForwardDelay {
      type int32;
      units "seconds";
      config false;
      description
       "This time value, measured in units of hundredths of a
        second, controls how fast a port changes its spanning
        state when moving towards the Forwarding state.  The
        value determines how long the port stays in each of the
        Listening and Learning states, which precede the
        Forwarding state.  This value is also used when a
        topology change has been detected and is underway, to
        age all dynamic entries in the Forwarding Database.
        [Note This is
        the provisioned value of the local bridge, in contrast to
        ForwardDelay, which is the value that this
        bridge and all others would start using if/when this
        bridge were to become the root.]";
      reference
       "IEEE 802.1D-1998: clause 8.5.3.6";
    }
    leaf TxHoldCount {
		type int32;
		config false;
		description
		 "TODO";
    }
  }
}
  notification newRoot {
    description     
     "The newRoot trap indicates that the sending agent has
      become the new root of the Spanning Tree; the trap is
      sent by a bridge soon after its election as the new
      
      
      
      root, e.g., upon expiration of the Topology Change Timer,
      immediately subsequent to its election.  Implementation
      of this trap is optional.";

  }

  notification topologyChange {
    description     
     "A topologyChange trap is sent by a bridge when any of
      its configured ports transitions from the Learning state
      to the Forwarding state, or from the Forwarding state to
      the Blocking state.  The trap is not sent if a newRoot
      trap is sent for the same transition.  Implementation of
      this trap is optional.";

  }
} /* end of module BRIDGE-MIB */
