module openconfig-if-aggregate {

  yang-version "1";

  // namespace
  namespace "http://openconfig.net/yang/interface/aggregate";

  prefix "lag";

  import ietf-yang-types { prefix yang; }
  
  // meta
  organization "SnapRoute";

  description
    "Model for managing aggregated interfaces, including LACP, DR, IPP-
    managed aggregates";

  revision "2016-08-16" {
    description
      "Initial SnapRoute public release";
    reference "0.1.1";
  }


  // extension statements

  // feature statements

  // identity statements

  // typedef statements

  typedef lacp-activity-type {
    type enumeration {
      enum ACTIVE {
        description
          "Interface is an active member, i.e., will detect and
          maintain aggregates";
      }
      enum PASSIVE {
        description
          "Interface is a passive member, i.e., it participates
          with an active partner";
      }
    }
    description
      "Describes the LACP membership type, active or passive, of the
      interface in the aggregate";
    reference "IEEE 802.1AX-2008";
  }

  typedef lacp-timeout-type {
    type enumeration {
      enum LONG {
        description
          "Participant wishes to use long timeouts to detect
          status of the aggregate, i.e., will expect less frequent
          transmissions. Long timeout is 90 seconds.";
      }
      enum SHORT {
        description
          "Participant wishes to use short timeouts, i.e., expects
          frequent transmissions to aggressively detect status
          changes. Short timeout is 3 seconds.";
      }
    }
    description
      "Type of timeout used, short or long, by LACP participants";
    reference "IEEE 802.1AX-2008";
  }

  typedef lacp-synchronization-type {
    type enumeration {
      enum IN_SYNC {
        description
          "Participant is in sync with the system id and key
          transmitted";
      }
      enum OUT_SYNC {
        description
          "Participant is not in sync with the system id and key
          transmitted";
      }
    }
    description
      "Indicates LACP synchronization state of participant";
    reference "IEEE 802.1AX-2008";
  }

  typedef lacp-period-type {
    type enumeration {
      enum FAST {
        description "Send LACP packets every second";
      }
      enum SLOW {
        description "Send LACP packets every 30 seconds";
      }
    }
    description
      "Defines the period options for the time between sending
      LACP messages";
    reference "IEEE 802.3ad";
  }

  typedef aggregation-type {
    type enumeration {
      enum LACP {
        description "LAG managed by LACP";
      }
      enum STATIC {
        description "Statically configured bundle / LAG";
      }
    }
    description
      "Type to define the lag-type, i.e., how the LAG is
      defined and managed";
  }

  typedef aggregation-hash {
	type enumeration {
		enum LAYER2 {
			description "Uses XOR of hardware MAC addresses and packet type ID
		field to generate the hash. The formula is

		hash = source MAC XOR destination MAC XOR packet type ID
		slave number = hash modulo slave count

		This algorithm will place all traffic to a particular
		network peer on the same slave.

		This algorithm is 802.3ad compliant.";
		}
		enum LAYER2_3 {
			description "This policy uses a combination of layer2 and layer3
		protocol information to generate the hash.

		Uses XOR of hardware MAC addresses and IP addresses to
		generate the hash.  The formula is

		hash = source MAC XOR destination MAC XOR packet type ID
		hash = hash XOR source IP XOR destination IP
		hash = hash XOR (hash RSHIFT 16)
		hash = hash XOR (hash RSHIFT 8)
		And then hash is reduced modulo slave count.

		If the protocol is IPv6 then the source and destination
		addresses are first hashed using ipv6_addr_hash.

		This algorithm will place all traffic to a particular
		network peer on the same slave.  For non-IP traffic,
		the formula is the same as for the layer2 transmit
		hash policy.

		This policy is intended to provide a more balanced
		distribution of traffic than layer2 alone, especially
		in environments where a layer3 gateway device is
		required to reach most destinations.

		This algorithm is 802.3ad compliant.";
		}
		enum LAYER3_4 {
			description "This policy uses upper layer protocol information,
		when available, to generate the hash.  This allows for
		traffic to a particular network peer to span multiple
		slaves, although a single connection will not span
		multiple slaves.

		The formula for unfragmented TCP and UDP packets is

		hash = source port, destination port (as in the header)
		hash = hash XOR source IP XOR destination IP
		hash = hash XOR (hash RSHIFT 16)
		hash = hash XOR (hash RSHIFT 8)
		And then hash is reduced modulo slave count.

		If the protocol is IPv6 then the source and destination
		addresses are first hashed using ipv6_addr_hash.

		For fragmented TCP or UDP packets and all other IPv4 and
		IPv6 protocol traffic, the source and destination port
		information is omitted.  For non-IP traffic, the
		formula is the same as for the layer2 transmit hash
		policy.

		This algorithm is not fully 802.3ad compliant.  A
		single TCP or UDP conversation containing both
		fragmented and unfragmented packets will see packets
		striped across two interfaces.  This may result in out
		of order delivery.  Most traffic types will not meet
		this criteria, as TCP rarely fragments traffic, and
		most UDP traffic is not involved in extended
		conversations.  Other implementations of 802.3ad may
		or may not tolerate this noncompliance.";
		}
	}
  }

  typedef rx-machine-state {
	type enumeration {
		enum RX_CURRENT {
			description "LACP Rx Machine Current State";
		}
		enum RX_EXPIRED {
			description "LACP Rx Machine Expired State";
		}
  		enum RX_DEFAULTED {
			description "LACP Rx Machine Defaulted State";
		}
		enum RX_INITIALIZE {
			description "LACP Rx Machine Initialize State";
		}
		enum RX_LACP_DISABLED {
			description "LACP Rx Machine LACP Disabled State";
		}
		enum RX_PORT_DISABLE {
			description "LACP Rx Machine Port Disabled State";
		}		
	}
  }



  typedef mux-machine-state {
	type enumeration {
		enum MUX_DETACHED {
			description "LACP MUX Machine Detached State";
		}
		enum MUX_WAITING {
			description "LACP MUX Machine Waiting State";
		}
		enum MUX_ATTACHED {
			description "LACP MUX Machine Attached State";
		}
		enum MUX_COLLECTING {
			description "LACP MUX Machine Collecting State";
		}
		enum MUX_DISTRIBUTING {
			description "LACP MUX Machine Distributing State";
		}
		enum MUX_COLLECTING_DISTRIBUTING {
			description "LACP MUX Machine Collecting Distributing State";
		}
		enum MUX_DISTRIBUTING_DEFAULTED {
		    description "LACP MUX Machine Distributing State and Defaulted";
		}
		enum MUX_COLLECTING_DISTRIBUTING_DEFAULTED {
			description "LACP MUX Machine Collecting Distributing State and Defaulted";
		}
	}
  }

  typedef churn-machine-state {
	type enumeration {
		enum CHURN_NO_CHURN {
			description "LACP Churn Machine No Churn State";
		}
		enum CHURN_CHURN {
			description "LACP Churn Machine Churn State";
		}
	} 
  }

	typedef drcp-rx-machine-state {
		type enumeration {
			enum CURRENT {
				description "CURRENT state";
			}
			enum EXPIRED {
				description "expired state";
			}
			enum DEFAULTED {
				description "DEFAULTED state";
			}
			enum INITIALIZE {
				description "INITIALIZE state";
			}
			enum REPORT_TO_MANAGEMENT {
			    description "REPORT_TO_MANAGEMENT state";
			}
		}
	}


  // grouping statements

  grouping aggregation-lacp-config {
    description
      "Configuration data for LACP aggregate interfaces";

    leaf interval {
      type lacp-period-type;
      default SLOW;
      config true;
      description
        "Set the period between LACP messages -- uses
        the lacp-period-type enumeration.";
    }

    leaf lacp-mode {
      type lacp-activity-type;
      default ACTIVE;
      config true;
      description
        "ACTIVE is to initiate the transmission of LACP packets.
         PASSIVE is to wait for peer to initiate the transmission of
         LACP packets.";
        //TODO:some implementations configure the LACP mode on each
        //member interface rather than on the LAG interface.  There
        //may be use cases for this identified at a later time.
    }

    leaf system-id-mac {
      type yang:mac-address;
      config true;
      default "00:00:00:00:00:00";
      description
        "The MAC address portion of the nodes System ID. This is
        combined with the system priority to construct the 8-octet
        system-id";
    }

    leaf system-priority {
      type uint16;
      config true;
      default 32768;
      description
        "Sytem priority used by the node on this LAG interface.
        Lower value is higher priority for determining which node
        is the controlling system.";
    }
	
	leaf lag-hash {
		type aggregation-hash;
		default LAYER2;
		config true;
		description
		   "The tx hashing algorithm used by the lag group";
	}
	leaf admin-state {
       type string;
       config true;
       default "enable";
       description
          "Convenient way to disable/enable a lag group.  The behaviour should be such
           that all traffic should stop.  LACP frames should continue to be processed";
    }
  }

grouping aggregation-lacp-state {
    description
      "Configuration data for LACP aggregate interfaces";

    leaf interval {
      type lacp-period-type;
      default SLOW;
      config false;
      description
        "Set the period between LACP messages -- uses
        the lacp-period-type enumeration.";
    }

    leaf lacp-mode {
      type lacp-activity-type;
      default ACTIVE;
      config false;
      description
        "ACTIVE is to initiate the transmission of LACP packets.
         PASSIVE is to wait for peer to initiate the transmission of
         LACP packets.";
        //TODO:some implementations configure the LACP mode on each
        //member interface rather than on the LAG interface.  There
        //may be use cases for this identified at a later time.
    }

    leaf system-id-mac {
      type yang:mac-address;
      config false;
      description
        "The MAC address portion of the nodes System ID. This is
        combined with the system priority to construct the 8-octet
        system-id";
    }

    leaf system-priority {
      type uint16;
      config false;
      description
        "Sytem priority used by the node on this LAG interface.
        Lower value is higher priority for determining which node
        is the controlling system.";
    }

	leaf lag-hash {
		type aggregation-hash;
		default LAYER2;
		config false;
		description
		   "The tx hashing algorithm used by the lag group";
	}

	leaf admin-state {
       type string;
       config false;
       description
          "Convenient way to disable/enable a lag group.  The behaviour should be such
           that all traffic should stop.  LACP frames should continue to be processed";
    }

    leaf oper-state {
       type string;
       config false;
       description
          "Operational status of the lag group.  If all ports are DOWN this will display
           DOWN.  If the group was admin disabled then will display DOWN.  No ports
           configured in group will display DOWN";
    }
  }


  
  grouping aggregation-lacp-members-state {
    description
      "Operational status data for the member interfaces";

    leaf IfIndex {
      //type ocif:interface-ref;
      type int32;
      config false;
      description
        "Interface member of the LACP aggregate";
    }
	
    leaf activity {
      type lacp-activity-type;
      config false;
      description "Indicates participant is active or passive";
    }

    leaf timeout {
      type lacp-timeout-type;
      description
        "The timeout type (short or long) used by the
        participant";
    }

    leaf synchronization {
      type lacp-synchronization-type;
      config false;
      description
        "Indicates whether the participant is in-sync or
        out-of-sync";
    }

    leaf aggregatable {
      type boolean;
      config false;
      description
        "A true value indicates that the participant will allow
        the link to be used as part of the aggregate. A false
        value indicates the link should be used as an individual
        link";
    }

    leaf collecting {
      type boolean;
      config false;
      description
        "If true, the participant is collecting incoming frames
        on the link, otherwise false";
    }

    leaf distributing {
      type boolean;
      config false;
      description
        "When true, the participant is distributing outgoing
        frames; when false, distribution is disabled";
    }

    leaf defaulted {
      type boolean;
      config false;
      description
         "When no partner information is exchanged port will come up in a
          defaulted state";
    }

    leaf system-id {
      type yang:mac-address;
      config false;
      description
        "MAC address that defines the local system ID for the
        aggregate interface";
    }

    leaf oper-key {
      type uint16;
      config false;
      description
        "Current operational value of the key for the aggregate
        interface";
    }

    leaf partner-id {
      type yang:mac-address;
      config false;
      description
        "MAC address representing the protocol partners interface
        system ID";
    }

    leaf partner-key {
      type uint16;
      config false;
      description
        "Operational value of the protocol partners key";
    }

	// same as AggregationPort
	leaf debug-id {
		type uint32;
                config false;
		description 
			"Debug Information Id";
	}
	
	leaf rx-machine {
		type rx-machine-state;
      config false;
		description
			"Current Rx Machine State";
	}
	
	leaf rx-time {
		type uint32;
      config false;
		description
			"Time at which the last LACPDU was received by a given port, 
			in terms of centiseconds since the system was last reset";
	}
	
	leaf mux-machine {
		type mux-machine-state;
      config false;
		description
			"Current MUX Machine State";
	}
	
	leaf mux-reason {
		type string;
      config false;
		description
			"Reason for the most recent MUX state change";
	} 
	
	leaf actor-churn-machine {
		type churn-machine-state;
      config false;
		description
			"Actor Churn Detection Machine State";
	}
	
	leaf partner-churn-machine {
		type churn-machine-state;
      config false;
		description
			"Partner Churn Detection Machine State";
	}
	
	leaf actor-churn-count {
		type yang:counter64;
      config false;
		description
			"Number of times the Actor State machine has entered the 
			ACTOR_CHURN state";
	}
	
	leaf partner-churn-count {
		type yang:counter64;
      config false;
		description
			"Number of times the Partner State machine has entered the 
			ACTOR_CHURN state";
	}
	
	leaf actor-sync-transition-count {
		type yang:counter64;
      config false;
		description
			"Number of times the Actors Mux state machine has entered the 
			IN_SYNC state.";
	} 
	
	leaf partner-sync-transition-count {
		type yang:counter64;
      config false;
		description
			"Number of times the Partners Mux state machine has entered the 
			IN_SYNC state.";
	} 
	
	leaf actor-change-count {
		type yang:counter64;
      config false;
		description
			"Number of times the Actors perception of the LAG ID for the 
			Aggregation Port has changed.";
	}
	
	leaf partner-change-count {
		type yang:counter64;
      config false;
		description
			"Number of times the Partners perception of the LAG ID for the 
			Aggregation Port has changed.";
	}
	
	leaf actor-cds-churn-machine {
		type churn-machine-state;
      config false;
		description
			"If supported Actor CDS Churn Machine State";
	}
	
	leaf partner-cds-churn-machine {
		type churn-machine-state;
      config false;
		description
			"If supported Partner CDS Churn Machine State";
	}
	
	leaf actor-cds-churn-count {
		type yang:counter64;
      config false;
		description
			"If supported the number of times the Actor CDS Churn state
			has entered the ACTOR_CDS_CHURN state";
	}
	
	leaf partner-cds-churn-count {
		type yang:counter64;
      config false;
		description
			"If supported the number of times the Actor CDS Churn state
			has entered the ACTOR_CDS_CHURN state";
	}
    // TODO: rjs: unclear whether this is required, it is referenced
    //            elsewhere under the state container. The grouping
    //            does not exist.
    // added the new group below to provide LACP statistics.
    // uses aggregation-lacp-statistic;
  }

grouping aggregation-lacp-members-statistics {
    description
      "LACP packet statistics for the member interfaces";

      leaf lacp-in-pkts {
        type yang:counter64;
      config false;
        description
          "Number of LACPDUs received";
      }

      leaf lacp-out-pkts {
        type yang:counter64;
      config false;
        description
          "Number of LACPDUs transmitted";
      }

      leaf lacp-rx-errors {
        type yang:counter64;
      config false;
        description
          "Number of LACPDU receive packet errors";
      }

      leaf lacp-tx-errors {
        type yang:counter64;
      config false;
        description
          "Number of LACPDU transmit packet errors";
      }

      leaf lacp-unknown-errors {
        type yang:counter64;
      config false;
        description
          "Number of LACPDU unknown packet errors";
      }

      leaf lacp-errors {
        type yang:counter64;
      config false;
        description
          "Number of LACPDU illegal packet errors";
      }
		
	  leaf lamp-in-pdu {
		type yang:counter64;
      config false;
		description
			"Number of LAMPDU received";	
	  }
	
	  leaf lamp-in-response-pdu {
		type yang:counter64;
      config false;
		description
			"Number of LAMPDU Response received";
	  }
	
	  leaf lamp-out-pdu {
		type yang:counter64;
      config false;
		description
			"Number of LAMPDU transmited";	
	  }
	
	  leaf lamp-out-response-pdu {
		type yang:counter64;
      config false;
		description
			"Number of LAMPDU Response received";
	  }
  }

  grouping aggregation-logical-config {
    description
      "Configuration data for aggregate interfaces";


    leaf lag-type {
      type aggregation-type;
      config true;
      default LACP;
      description
        "Sets the type of LAG, i.e., how it is
        configured / maintained";
    }

    leaf min-links {
      type uint16;
      config true;
      default 1;
      description
        "Specifies the mininum number of member
        interfaces that must be active for the aggregate interface
        to be available";
    }

  }

  grouping aggregation-logical-state {
    description
      "Configuration data for aggregate interfaces";

    leaf IfIndex {
      type int32;
      config false;
      description
         "the ifindex of the bonded interface";
    }

    leaf lag-type {
      type aggregation-type;
      config false;
      description
        "Sets the type of LAG, i.e., how it is
        configured / maintained";
    }

    leaf min-links {
      type uint16;
      config false;
      description
        "Specifies the mininum number of member
        interfaces that must be active for the aggregate interface
        to be available";
    }

  }

  grouping aggregation-lacp-members-top {
    description
      "Top-level grouping for aggregate members list";

    container Intf {
      config false;
      description
        "Enclosing container for the list of members interfaces of
        the aggregate. This list is considered operational state
        only so is labeled config false and has no config container";

      list RefList {
        key  IntfRef;
        description
          "List of member interfaces and their associated status for
          a LACP-controlled aggregate interface.  Member list is not
          configurable here -- each interface indicates items
          its participation in the LAG.";

        leaf IntfRef {
          type string; 
          config false;
	      description
            "Reference to aggregate member interface";
        }


        container state {

          config false;

          description
            "Operational state data for aggregate members";

	      leaf oper-state {
             type string;
	         description
               "The operation state, typically UP IN BUNDLE, or DOWN";
          }
          uses aggregation-lacp-members-state;
          uses aggregation-lacp-members-statistics;
        }
      }
    }
  }

  container la-port-channel {
       config false;
       description
          "Port Channel Member States container";
	   
	   leaf LagIntfRef {
          type string;
		 config false;
          description "Id of the lag group to which this port is associated with";
        }
       uses aggregation-lacp-members-top;
  }

  list la {
    description "Top-level data definitions for LAGs";
    key IntfRef;

    leaf IntfRef {
        type string;
        description "Id of the lag group";
    }

    container port {

      presence "Sets the interface to be a logical aggregate / LAG";
      description
        "Options for logical interfaces representing
        aggregates";

      container channel {
        description
          "Configuration variables for logical aggregate /
          LAG interfaces";

        uses aggregation-logical-config;
        uses aggregation-lacp-config;
        leaf-list IntfRefList {
          //TODO: this should be active only for non-LACP LAGs,
          //otherwise the LAG state has the list of members and
          // their status
          when "lag:lag-type = 'STATIC'" {
            description
              "The simple list of member interfaces is active
              when the aggregate is statically configured";
          }
          type string;
          config true;
          description
            "List of current member interfaces for the aggregate,
            expressed as references to existing interfaces";
          }
      }

      container channel-state {

        config false;
        description
          "Operational state variables for logical
          aggregate / LAG interfaces";

        uses aggregation-logical-state;
        uses aggregation-lacp-state;
        //TODO: identity other state variable as the LAG level

        leaf-list IntfRefList {
          //TODO: this should be active only for non-LACP LAGs,
          //otherwise the LAG state has the list of members and
          // their status
          when "lag:lag-type = 'STATIC'" {
            description
              "The list of member interfaces is active
              when the aggregate is up in bundle";
          }
          type string;
          config false;
          description
            "List of current member interfaces for the aggregate,
            expressed as references to existing interfaces";
        }

        leaf-list IntfRefList-up-in-bundle {
          //TODO: this should be active only for non-LACP LAGs,
          //otherwise the LAG state has the list of members and
          // their status
          when "lag:lag-type = 'STATIC'" {
            description
              "The list of member interfaces is active
              when the aggregate is up in bundle";
          }
          type string;
          config false;
          description
            "List of current member interfaces for the aggregate,
            expressed as references to existing interfaces";
        }
      }
    }
  }

  grouping distributed-relay-state {
		
	leaf description {
      type string;
      description
        "A human-readable text string containing information about the Distribute Relay. This string
		is read-only. The contents are vendor specific";
    	}

  	leaf portal-address {
      type yang:mac-address;
	  description
        "A read-write identifier of a particular Portal. Portal-Addr has to be unique among at least
		all of the potential Portal Systems to which a given Portal System might be attached via an
		IPL Intra-Portal Link. Also used as the Actors System ID (6.3.2) for the emulated system";
    	}
		
	leaf portal-priority {
		type uint16;
		description 
		  "A 2 octet read-write value indicating the priority value associated with the Portals System
		   ID. Also used as the Actors System Priority (6.3.2) for the emulated system.";
	}
	
	leaf three-portal-system {
		type boolean;
		description 
		  "A read-write Boolean value indicating whether this Portal System is part of a Portal
			consisting of three Portal Systems or not. Value 1 stands for a Portal of three Portal Systems,
			value 0 stands for a Portal of two or one Portal Systems. The default value is 0";
	}

	leaf portal-system-number {
		type uint8;
		description
		   "A read-write identifier of this particular Portal System within a Portal. It is the responsibility
		    of the network administrator to ensure that these numbers are unique among the Portal
		    Systems with the same aDrniPortalAddr (7.4.1.1.4)";
	}

	// intra portal links
	leaf-list intfreflist {
          type string;
          description
            "Read-write list of the Interface Identifiers of the Ports to the Intra-Portal Links assigned to
			this Distributed Relay. Each Interface Identifier, a Port ID (6.3.4), has the two least
			significant bits of its Port Priority (7.3.2.1.15) configured to match the Portal System Number
			of the attached Portal System. The number of IPLs in the list depends on the Portal topology.
			For a Portal of three Portal Systems two or three IPLs can be used, for a Portal of two Portal
			Systems a single IPL is required and for a single Portal System no IPL is required";
    }
	
	leaf IntfRef {
		type string;
		description
		   "Read-write Interface Identifier of the Aggregator Port assigned to this Distributed Relay";		
	}
	
	leaf-list conv-admin-gateway {
		type uint32;
		description
		   "There are 4096 aDrniConvAdminGateway[] variables, aDrniConvAdminGateway[0]
			through aDrniConvAdminGateway[4095], indexed by Gateway Conversation ID. Each
			contains administrative values of the Gateway selection priority list for the Distributed Relay
			for the referenced Gateway Conversation ID. This selection priority list, a sequence of
			integers for each Gateway Conversation ID, is a list of Portal System Numbers in the order of
			preference, highest to lowest, for the corresponding preferred Portal Systems Gateway to
			carry that Conversation.";
	}

	leaf-list neighbor-admin-conv-gateway-list-digest {
		type uint8;
		description
		 "The value for the digest of the prioritized Gateway Conversation ID-to-Gateway assignments
		  of the Neighbor Portal System, assigned by administrator or System policy for use when the
		  Neighbor Portal System’s information is unknown";
	}
	
	leaf-list neighbor-admin-conv-port-list-digest {
		type uint8;
		description
		 "The value for the digest of the prioritized Port Conversation ID-to-Aggregation Port
		  assignments of the Neighbor Portal System, assigned by administrator or System policy for
		  use when the Neighbor Portal System’s information is unknown";
	}
	
	leaf gateway-algorithm {
		type string;
		description
		   "This object identifies the algorithm used by the DR Function to assign frames to a Gateway
			Conversation ID. Table 9-7 provides the IEEE 802.1 OUI (00:80:C2) Gateway Algorithm
			encodings";
	}
	
	leaf neighbor-gateway-algorithm {
		type string;
		description
		   "TThis object identifies the value for the Gateway algorithm of the Neighbor Portal System,
		    assigned by administrator or System policy for use when the Neighbor Portal System’s
		    information is unknown. Table 9-7 provides the IEEE 802.1 OUI (00-80-C2) Gateway
			Algorithm encodings";
	}
	
	leaf neighbor-port-algorithm {
		type string;
		description
		   "This object identifies the value for the Port Algorithm of the Neighbor Portal System,
			assigned by administrator or System policy for use when the Neighbor Portal System’s
			information is unknown. Table 6-4 provides the IEEE 802.1 OUI (00-80-C2) Port Algorithm
			encodings.";
	}
	
	leaf neighbor-Admin-DRCP-State {
		type string;
		description
		   "A string of 8 bits, corresponding to the administrative values of DRCP_State [item s) in
			9.4.3.2] as transmitted by this Portal System in DRCPDUs. The first bit corresponds to bit 0
			of DRCP_State (Home_Gateway), the second bit corresponds to bit 1 (Neighbor_Gateway),
			the third bit corresponds to bit 2 (Other_Gateway), the fourth bit corresponds to bit 3
			(IPP_Activity), the fifth bit corresponds to bit 4 (DRCP_Timeout), the sixth bit corresponds
			to bit 5 (Gateway_Sync), the seventh bit corresponds to bit 6 (Port_Sync), and the eighth bit
			corresponds to bit 7 (Expired). These values allow administrative control over the values of
			Home_Gateway, Neighbor_Gateway, Other_Gateway, IPP_Activity, and DRCP_Timeout.";
	}
	
	leaf encap-method {
		type string;
		description
		   "This managed object is applicable only when Network / IPL sharing by time (9.3.2.1) or
			Network / IPL sharing by tag (9.3.2.2) or Network / IPL sharing by encapsulation (9.3.2.3) is
			supported. The object identifies the value representing the encapsulation method that is used
			to transport IPL frames to the Neighbor Portal System when the IPL and network link are
			sharing the same physical link. It consists of the 3-octet OUI or CID identifying the
			organization that is responsible for this encapsulation and one following octet used to identify
			the encapsulation method defined by that organization. Table 9-11 provides the IEEE 802.1
			OUI (00-80-C2) encapsulation method encodings. A Default value of 0x00-80-C2-00
			indicates that the IPL is using a separate physical or Aggregation link. A value of 1 indicates
			that Network / IPL sharing by time (9.3.2.1) is used. A value of 2 indicates that the
			encapsulation method used is the same as the one used by network frames and that Network /
			IPL sharing by tag (9.3.2.2) is used";
	}
	
	leaf-list IPL-Encap-Map {
		type uint32;
		description
		   "This managed object is applicable only when Network / IPL sharing by tag (9.3.2.2) or
			Network / IPL sharing by encapsulation (9.3.2.3) is supported. Each entry represents the
			value of the identifier used for an IPL frame associated with that Gateway Conversation ID
			for the encapsulation method specified in 7.4.1.1.17. There are 1024 possible Conversation Ids
			in a three portal system";
	}
	
	leaf-list Net-Encap-Map {
		type uint32;
		description
		   "This managed object is applicable only when Network / IPL sharing by tag (9.3.2.2) is
			supported. Each entry represents the translated value of the identifier used for a network
			frame associated with that Gateway Conversation ID when the method specified in 7.4.1.1.17
			is the Network / IPL sharing by tag method specified in 9.3.2.2 and the network frames need
			to share the tag space used by IPL frames";
	}
	
	leaf-list DR-Port-Conversation-Passes {
		type uint8;
		description
		   "A read-only current operational vector of Boolean values, with one value for each possible
			Port Conversation ID. A 1 indicates that the Port Conversation ID is allowed to be distributed
			through this DR Function’s Aggregator, and a 0 indicates that it cannot.
			aDrniDRPortConversationPasses is referencing the current value of 
			Drni_Portal_System_Port_Conversation ()";
	}

	leaf-list DR-Gateway-Conversation-Passes {
		type uint8;
		description
		   "A read-only current operational vector of Boolean values, with one value for each possible
			Port Conversation ID. A 1 indicates that the Port Conversation ID is allowed to be distributed
			through this DR Function’s Aggregator, and a 0 indicates that it cannot.
			aDrniDRPortConversationPasses is referencing the current value of 
			Drni_Portal_System_Port_Conversation ()";
	}
	
	leaf PSI {
	    type boolean;
	    description
	       "A read-only Boolean value providing the value of PSI, which indicates whether this Portal
		    System is isolated from the other Portal Systems within the same Portal (“TRUE”) or not
		    (“FALSE”)";
	}

	leaf-list Port-Conversation-Control {
	    type boolean;
	    description
	       "A read-write Boolean value that controls the operation of the updateDRFHomeState (9.4.11).
			When set to TRUE the Home Gateway Vector is set equal to
			Drni_Portal_System_Port_Conversation. Setting this object to TRUE is only possible when
			the Gateway algorithm and the Port algorithm use the same distributions methods. The default
			is FALSE, indicating that the Home Gateway Vector is controlled by the network control
			protocol";
	}

	leaf Intra-Portal-Port-Protocol-DA {
	    type yang:mac-address;
	  	description
	       "A 6-octet read-write MAC Address value specifying the DA to be used when
			sending DRCPDUs, corresponding to the value of DRCP_Protocol_DA in 9.4.4.1.3. Its
			values is one of the addresses selected from Table 9-6 and its default shall be the IEEE 802.1
			Nearest non-TPMR Bridge group address (01-80-C2-00-00-03).";
	}
		
  }

  grouping distributed-relay-config {
	description "Configuration data for Distributed Relay System / MLAG";

    leaf portal-address {
      type string;
	  config true;
	  description
        "A read-write identifier of a particular Portal. Portal-Addr has to be unique among at least
		all of the potential Portal Systems to which a given Portal System might be attached via an
		IPL Intra-Portal Link. Also used as the Actors System ID (6.3.2) for the emulated system";
    	}
		
	leaf portal-priority {
		type uint16 {
			range 1..65535;
		}
		config true;
		default 32768;
		description 
		  "A 2octet read-write value indicating the priority value associated with the Portals System
		   ID. Also used as the Actors System Priority (6.3.2) for the emulated system.";
	}
	
	leaf three-portal-system {
		type boolean;
		config true;
		default false;
		description 
		  "A read-write Boolean value indicating whether this Portal System is part of a Portal
			consisting of three Portal Systems or not. Value 1 stands for a Portal of three Portal Systems,
			value 0 stands for a Portal of two or one Portal Systems. The default value is 0";
	}

	leaf portal-system-number {
		type uint8 {
			range 1..2;
		}
		config true;
		description
		   "A read-write identifier of this particular Portal System within a Portal. It is the responsibility
		    of the network administrator to ensure that these numbers are unique among the Portal
		    Systems with the same aDrniPortalAddr (7.4.1.1.4)";
	}

	// intra portal links
	leaf-list intfreflist {
          type string;
          config true;
          description
            "Read-write list of the Interface Identifiers of the Ports to the Intra-Portal Links assigned to
			this Distributed Relay. Each Interface Identifier, a Port ID (6.3.4), has the two least
			significant bits of its Port Priority (7.3.2.1.15) configured to match the Portal System Number
			of the attached Portal System. The number of IPLs in the list depends on the Portal topology.
			For a Portal of three Portal Systems two or three IPLs can be used, for a Portal of two Portal
			Systems a single IPL is required and for a single Portal System no IPL is required";

    }
	
	leaf IntfRef {
		type string;
		config true;
		description
		   "Read-write Interface Identifier of the Aggregator Port assigned to this Distributed Relay";		
	}
	
	//leaf-list conv-admin-gateway {
	//	type uint32;
	//	config true;
	//	default [];
	//	description
	//	   "There are 4096 aDrniConvAdminGateway[] variables, aDrniConvAdminGateway[0]
	//		through aDrniConvAdminGateway[4095], indexed by Gateway Conversation ID. Each
	//		contains administrative values of the Gateway selection priority list for the Distributed Relay
	//		for the referenced Gateway Conversation ID. This selection priority list, a sequence of
	//		integers for each Gateway Conversation ID, is a list of Portal System Numbers in the order of
	//		preference, highest to lowest, for the corresponding preferred Portal Systems Gateway to
	//		carry that Conversation.";
	//}
	//leaf-list neighbor-admin-conv-gateway-list-digest {
	//	type uint8;
	//	config true;
	//	
	//	description
	//	 "The value for the digest of the prioritized Gateway Conversation ID-to-Gateway assignments
	//	  of the Neighbor Portal System, assigned by administrator or System policy for use when the
	//	  Neighbor Portal System’s information is unknown";
	//}
	
	//leaf-list neighbor-admin-conv-port-list-digest {
	//	type uint8;
	//	config true;
	//	description
	//	 "The value for the digest of the prioritized Port Conversation ID-to-Aggregation Port
	//	  assignments of the Neighbor Portal System, assigned by administrator or System policy for
	//	  use when the Neighbor Portal System’s information is unknown";
	//}
	
	leaf gateway-algorithm {
		type string;
		config true;
		default "00-80-C2-01";
		description
		   "This object identifies the algorithm used by the DR Function to assign frames to a Gateway
			Conversation ID. Table 9-7 provides the IEEE 802.1 OUI (00:80:C2) Gateway Algorithm
			encodings";
	}
	
	leaf neighbor-gateway-algorithm {
		type string;
		config true;
		default "00-80-C2-01";
		description
		   "TThis object identifies the value for the Gateway algorithm of the Neighbor Portal System,
		    assigned by administrator or System policy for use when the Neighbor Portal Systems
		    information is unknown. Table 9-7 provides the IEEE 802.1 OUI (00-80-C2) Gateway
			Algorithm encodings";
	}
	
	leaf neighbor-port-algorithm {
		type string;
		config true;
		default "00-80-C2-01";
		description
		   "This object identifies the value for the Port Algorithm of the Neighbor Portal System,
			assigned by administrator or System policy for use when the Neighbor Portal System’s
			information is unknown. Table 6-4 provides the IEEE 802.1 OUI (00-80-C2) Port Algorithm
			encodings.";
	}
	
	leaf neighbor-Admin-DRCP-State {
		type string;
		config true;
		default "00000000";
		description
		   "A string of 8 bits, corresponding to the administrative values of DRCP_State [item s) in
			9.4.3.2] as transmitted by this Portal System in DRCPDUs. The first bit corresponds to bit 0
			of DRCP_State (Home_Gateway), the second bit corresponds to bit 1 (Neighbor_Gateway),
			the third bit corresponds to bit 2 (Other_Gateway), the fourth bit corresponds to bit 3
			(IPP_Activity), the fifth bit corresponds to bit 4 (DRCP_Timeout), the sixth bit corresponds
			to bit 5 (Gateway_Sync), the seventh bit corresponds to bit 6 (Port_Sync), and the eighth bit
			corresponds to bit 7 (Expired). These values allow administrative control over the values of
			Home_Gateway, Neighbor_Gateway, Other_Gateway, IPP_Activity, and DRCP_Timeout.";
	}
	
	leaf encap-method {
		type string;
		config true;
		default "00-80-C2-01";
		description
		   "This managed object is applicable only when Network / IPL sharing by time (9.3.2.1) or
			Network / IPL sharing by tag (9.3.2.2) or Network / IPL sharing by encapsulation (9.3.2.3) is
			supported. The object identifies the value representing the encapsulation method that is used
			to transport IPL frames to the Neighbor Portal System when the IPL and network link are
			sharing the same physical link. It consists of the 3-octet OUI or CID identifying the
			organization that is responsible for this encapsulation and one following octet used to identify
			the encapsulation method defined by that organization. Table 9-11 provides the IEEE 802.1
			OUI (00-80-C2) encapsulation method encodings. A Default value of 0x00-80-C2-00
			indicates that the IPL is using a separate physical or Aggregation link. A value of 1 indicates
			that Network / IPL sharing by time (9.3.2.1) is used. A value of 2 indicates that the
			encapsulation method used is the same as the one used by network frames and that Network /
			IPL sharing by tag (9.3.2.2) is used";
	}
	
	//leaf-list IPL-Encap-Map {
	//	type string;
	//	config true;
	//	description
	//	   "This managed object is applicable only when Network / IPL sharing by tag (9.3.2.2) or
	//		Network / IPL sharing by encapsulation (9.3.2.3) is supported. Each entry represents the
	//		value of the identifier used for an IPL frame associated with that Gateway Conversation ID
	//		for the encapsulation method specified in 7.4.1.1.17. There are 1024 possible Conversation Ids
	//		in a three portal system";
	//}
	
	//leaf-list Net-Encap-Map {
	//	type uint32;
	//	config true;
	//	description
	//	   "This managed object is applicable only when Network / IPL sharing by tag (9.3.2.2) is
	//		supported. Each entry represents the translated value of the identifier used for a network
	//		frame associated with that Gateway Conversation ID when the method specified in 7.4.1.1.17
	//		is the Network / IPL sharing by tag method specified in 9.3.2.2 and the network frames need
	//		to share the tag space used by IPL frames";
	//}
	
	//leaf Port-Conversation-Control {
	//    type boolean;
	//	config true;
	//	default false;
	//    description
	//       "A read-write Boolean value that controls the operation of the updateDRFHomeState (9.4.11).
	//		When set to TRUE the Home Gateway Vector is set equal to
	//		Drni_Portal_System_Port_Conversation. Setting this object to TRUE is only possible when
	//		the Gateway algorithm and the Port algorithm use the same distributions methods. The default
	//		is FALSE, indicating that the Home Gateway Vector is controlled by the network control
	//		protocol";
	//}

	leaf Intra-Portal-Port-Protocol-DA {
	    type string;
	  	config true;
	  	default "01-80-C2-00-00-03";
	  	description
	       "A 6-octet read-write MAC Address value specifying the DA to be used when
			sending DRCPDUs, corresponding to the value of DRCP_Protocol_DA in 9.4.4.1.3. Its
			values is one of the addresses selected from Table 9-6 and its default shall be the IEEE 802.1
			Nearest non-TPMR Bridge group address (01-80-C2-00-00-03).";
	}
	
  }

  grouping ipp-link-statistics {

  	leaf DRCPDUsRx {
		type yang:counter64;
		config false;
		description
		    "The number of valid DRCPDUs received on this IPP.";
	}
	leaf DRCPDUsTx {
		type yang:counter64;
		config false;
		description
		    "The number of DRCPDUs transmitted on this IPP.";
	}
  }

  grouping ipp-link-debug {
	leaf DRCPRxState {
		type drcp-rx-machine-state;
		config false;
		description 
		 "This attribute holds the value current if the DRCPDU Receive state machine for the IPP is
		  in the CURRENT state, expired if the DRCPDU Receive state machine is in the EXPIRED
		  state, defaulted if the DRCPDU Receive state machine is in the DEFAULTED state,
		  initialize if the DRCPDU Receive state machine is in the INITIALIZE state, or
		  reportToManagement if the Receive state machine is in the REPORT_TO_MANAGEMENT state";
	}
	leaf LastRxTime {
		type uint32;
		config false;
		description
		    "The time at which the last DRCPDU was received by this IPP, in terms of centiseconds since
			the system was last reset. The ifLastChange object in the Interfaces MIB defined in IETF
			RFC 2863 is a suitable object for supplying a value for aIPPDebugLastRxTime";
	}
	
	leaf Diff-portal-reason {
		type string;
		description
			"A human-readable text string indicating the most recent set of variables that are responsible
			for setting the variable Differ_Portal or Differ_Conf_Portal (9.4.8) on this IPP to TRUE";
	}
  }

  grouping ipp-link-state {
	leaf IPPID {
		type uint32;
		config false;
		description
		  "The unique identifier allocated to this IPP by the local Portal System. This attribute identifies
			an IPP instance among the subordinate managed objects of the containing object.";
	}
	
	leaf Port-Conversation-Passes {
		type string;
		config false;
		description
		   "A read-only current operational vector of Boolean values, with one value for each possible
		  	Port Conversation ID. A 1 indicates that the Port Conversation ID is allowed to be
			transmitted through this IPP Intra-Portal Port, and a 0 indicates that it cannot.
			aIPPPortConversationPasses is referencing Ipp_Port_Conversation_Passes (9.3.4.3).";
	}
	
	leaf Gateway-Conversation-Direction {
		type string;
		config false;
		description
		   "A read-only current operational vector of Boolean values, with one value for each possible
		  	Port Conversation ID. A 1 indicates that the Port Conversation ID is allowed to be
			transmitted through this IPP Intra-Portal Port, and a 0 indicates that it cannot.
			aIPPPortConversationPasses is referencing Ipp_Port_Conversation_Passes (9.3.4.3).";
	}
	
	uses ipp-link-statistics;
	uses ipp-link-debug;
  }

  list ipp {
	description "Top-level data definitions for Distributed Relay / MLAGs IPP link";
     key "intfRef drNameRef";

     leaf intfRef {
        type string;
        description "A human-readable text string containing a locally significant name for the Distributed Relay IPP port link";
     }
	
	 leaf drNameRef {
		type string;
		description "A human-readable text string containing the Distributed Relay Instance name to which this IPP is associated";
	}
		
	container link-state {
		uses ipp-link-state;
	}
  }

  // 802.1ax-2014 Section 7.4.1.1 Distributed Relay
  list distributed {
  	description "Top-level data definitions for Distributed Relay / MLAGs";
     key drniName;

     leaf drniName {
        type string;
	    description "The unique identifier allocated to this Distributed Relay by the local System. This attribute
		identifies a Distributed Relay instance among the subordinate managed objects of the
		containing object.";
     }

	container relay {
		config true;
		uses distributed-relay-config;
	}
	
	container relay-state {
		config false;
		uses distributed-relay-state;
	}
  }
}
