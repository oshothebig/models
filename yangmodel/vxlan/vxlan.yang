module vxlan {
    namespace "urn:ietf:params:xml:ns:yang:ietf-vxlan";
    prefix "vxlan";

    import ietf-inet-types {
       prefix "inet";
    }

    import ietf-yang-types {
       prefix yang;
     }

    organization
      "IETF NVO3(Network Virtualization Overlays) Working Group";

      contact
       "
         editor:  <mailto:ccordes@snaproute.com>
        ";

    description
       "The YANG module defines a generic configuration
         model for VxLAN protocol";

    revision 2015-12-01 {
       description
         "02 revision.";
       reference
         "draft-chen-nvo3-vxlan-yang-02";
     }

    revision 2015-10-12 {
       description
         "01 revision.";
       reference
         "draft-chen-nvo3-vxlan-yang-01";
     }

    revision 2015-05-05 {
      description "Initial revision";
      reference
         "draft-chen-nvo3-vxlan-yang-00";
    }

    /* Typedefs  */

    typedef bgp-rt-type {
      type enumeration {
        enum import {
        description "For import";
       }
       enum export {
         description "For export";
       }
       enum both {
         description "For both import and export";
       }
     }
     description "BGP route-target type. Import from BGP YANG";
    }

    typedef vlan {
      type uint16 {
        range 1..4094;
      }
      description
      "Typedef for VLAN";
    }

    typedef vxlan-id {
      type uint32 {
         range 1..16777215;
      }
      description
        "Typedef for VxLAN ID.";
    }

    typedef access-type-vlan {
      type enumeration {
        enum access-type-vlan1to1 {
          description
            "Access type is VLAN 1:1.";
        }
        enum access-type-vlan1ton {
          description
            "Access type is VLAN 1:n.";
        }

      }
      default access-type-vlan1to1 ;
      description
        "VxLAN access type is VLAN.";
    }

    typedef access-type-mac {
       type empty ;
       description
         "VxLAN access type is MAC.";
    }

    typedef inner-vlan-handling-mode {
       type enumeration {
         enum discard-inner-vlan {
              description
                "Discard inner-VLAN.";
         }
         enum no-discard-inner-vlan {
              description
                "No discard inner-VLAN.";
         }
       }
       default discard-inner-vlan ;
       description
        "Typedef for inner-vlan-handling-mode";
    }

    typedef address-family-type {
       type enumeration {
         enum ipv4 {
           description
             "IPv4";
         }
         enum ipv6 {
           description
             "IPv6";
         }
       }
       description
         "Typedef for address family type.";
     }

    /* Configuration Data */

    container vxlan{
        list instance {
           key vxlan-id ;
		   config true;

           leaf vxlan-id {
             type vxlan-id;
             description
              "VxLAN ID or VNI";
           }
           leaf mc-dest-ip {
              type string;
              config true;
              mandatory true ;
              description
                 "VxLAN multicast IP address used when destination is uknown";
           }

           leaf vlan-id {
            type vlan;
            config true;
            description
                "Vlan associated with the Access targets.  Used in conjunction with a given VTEP
                 inner-vlan-handling-mode";
           }

           leaf mtu {
            type uint32;
            config true;
            default 1550;
            description
                "Set the MTU to be applied to all VTEP within this VxLAN";
           }
        }
        description
          "VxLAN instance.";

    container vtep {
            list instance {
               key "vtep-id";
               leaf vtep-id {
                  type uint32;
				config true;
                  description
                     "VTEP ID.";
                }

               leaf vtep-name{
                  type string;
				  config true;
                  description
                     "VTEP instance name. If not defined then one will be configured to be vtep<vtep-id>";
                }

               leaf src-ifIndex {
                  type int32;
				  config true;
                  description
                     "Source physical interface ifIndex.";
                }

                leaf UDP {
                   type uint16;
                   config true;
                   default 4789;
                   description
                       "vxlan udp port.  Deafult is the iana default udp port";
                }

                leaf TTL {
                    type uint16;
                    config true;
                    default 255;
                    description
                        "TTL of the Vxlan tunnel";
                }

                leaf TOS {
                    type uint16;
                    config true;
                    default 0;
                    description
                        "Type of Service";
                }

               leaf inner-vlan-handling-mode {
                  type inner-vlan-handling-mode;
				  config true;
                  description
                     "The inner vlan tag handling mode.";
                }

                leaf learning {
                   type boolean;
                   config true;
                   default true;
                   description
                    "specifies if unknown source link layer
                      addresses and IP addresses are entered into the VXLAN
                      device forwarding database.";
                }

                leaf rsc {
                    type boolean;
                    config true;
                    default false;
                    description
                     "specifies if route short circuit is turned on.";
                }

                leaf l2miss {
                    type boolean;
                    config true;
                    description
                        "specifies if netlink LLADDR miss notifications are generated.";
                }

                leaf l3miss {
                    type boolean;
                    config true;
                    description
                        "specifies if netlink IP ADDR miss
                      notifications are generated.";
                }

              leaf vxlan-id {
                type vxlan-id;
                config true;
                description
                   "VxLAN ID.";
              }

              leaf dst-ip {
                    type inet:ipv4-address;
                    config true;
                    description
                     "Destination IP address for the static VxLAN tunnel";
              }

              leaf src-ip {
                    type inet:ipv4-address;
                    config true;
                    description
                     "Source IP address for the static VxLAN tunnel, if not supplied switch default should be used.";
              }

              leaf src-mac {
                    type yang:mac-address;
                    config true;
                    description
                     "Source MAC for the static VxLAN tunnel, if not supplied switch default should be used.";
              }

              leaf vlan-id {
                type uint16;
                config true;
                description
                    "Vlan Id to encapsulate with the vtep tunnel ethernet header";
              }

            }
             description
                "VTEP instance.";
            }
     }

     // TODO add static binding for FDB entries
}
