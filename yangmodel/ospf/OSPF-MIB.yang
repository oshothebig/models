/*
 * This module has been generated by smidump 0.4.8:
 *
 *      smidump -f yang OSPF-MIB
 *
 * Do not edit. Edit the source file instead!
 */

module OSPF-MIB {

  /*** NAMESPACE / PREFIX DEFINITION ***/

  namespace "urn:ietf:params:xml:ns:yang:smiv2:OSPF-MIB";
  prefix "ospf-mib";

  /*** LINKAGE (IMPORTS / INCLUDES) ***/
/*
  import IF-MIB     { prefix "if-mib"; }
  import SNMPv2-TC  { prefix "smiv2"; }
  import inet-types { prefix "inet"; }
  import yang-types { prefix "yang"; }
*/

import ietf-yang-types { prefix yang; }
import ietf-inet-types { prefix inet; }

  /*** META INFORMATION ***/

  organization      
   "IETF OSPF Working Group";

  contact           
   "WG E-Mail: ospf@ietf.org
    
    WG Chairs: acee@cisco.com
               rohit@gmail.com
    
    Editors:   Dan Joyal
               Nortel
               600 Technology Park Drive
               Billerica, MA  01821
               djoyal@nortel.com
    
               Piotr Galecki
               Airvana
               19 Alpha Road
               Chelmsford, MA 01824
               pgalecki@airvana.com
    
               Spencer Giacalone
               CSFB
               Eleven Madison Ave
               New York, NY 10010-3629
               spencer.giacalone@gmail.com";

  description       
   "The MIB module to describe the OSPF Version 2
    Protocol.  Note that some objects in this MIB
    module may pose a significant security risk.
    Refer to the Security Considerations section
    in RFC 4750 for more information.
    
    Copyright (C) The IETF Trust (2006).
    This version of this MIB module is part of
    RFC 4750;  see the RFC itself for full legal
    notices.";

  revision "2006-11-10" {
    description     
     "Updated for latest changes to OSPF Version 2:
      - updated the General Group with the new
        ospfRFC1583Compatibility, ospfReferenceBandwidth
        and ospfDiscontinuityTime objects
      - added graceful-restart-related objects
      - added stub-router-related objects
      - updated the Area Table with NSSA-related objects
      - added ospfAreaAggregateExtRouteTag object
      - added Opaque LSA-related objects
      - updates to the Compliances and Security sections
      - added area LSA counter table
      - added section describing translation of notification
        parameters between SNMP versions
      - added ospfComplianceObsolete to contain obsolete
        object groups
      - deprecated ospfExtLsdbTable
      See Appendix B of RFC 4750 for more details.
      
      This version published as part of RFC 4750";
  }
  revision "1995-01-20" {
    description     
     "The initial SMIv2 revision of this MIB module, published
      in RFC 1850.";
  }

  /*** TYPE DEFINITIONS ***/

  typedef InterfaceIndexOrZero {
    type int32 {
      range "0..2147483647";
    }
    description
     "This textual convention is an extension of the
      InterfaceIndex convention.  The latter defines a greater
      than zero value used to identify an interface or interface
      sub-layer in the managed system.  This extension permits the
      additional value of zero.  the value zero is object-specific
      and must therefore be defined as part of the description of
      any object which uses this syntax.  Examples of the usage of
      zero might include situations where interface was unknown,
      or when none or all interfaces need to be referenced.";
  }

  typedef AreaID {
    type inet:ipv4-address;
    /*default "0.0.0.0";*/
    description     
     "An OSPF Area Identifier.
      Note that the Area ID, in OSPF, has the same format
      as an IP address, but has the function of defining
      a summarization point for link state advertisements.";
  }

  typedef RouterID {
    type inet:ipv4-address;
    /*default "0.0.0.0";*/
    description     
     "A OSPF Router Identifier.
      Note that the Router ID, in OSPF, has the same format
      as an IP address, but identifies the router independent
      
      of its IP address.";
  }

  typedef Metric {
    type int32 {
      range "0..65535";
    }
    description     
     "The OSPF internal metric.
      Note that the OSPF metric is defined as an unsigned value
      in the range.";
  }

  typedef BigMetric {
    type int32 {
      range "0..16777215";
    }
    description     
     "The OSPF external metric.";
  }

  typedef Status {
    type enumeration {
      enum enabled  { value 1; }
      enum disabled { value 2; }
    }
    description     
     "An indication of the operability of an OSPF
      function or feature.  For example, the status
      of an interface: 'enabled' indicates that
      it is willing to communicate with other OSPF routers,
      and 'disabled' indicates that it is not.";
  }

  typedef PositiveInteger {
    type int32 {
      range "0..2147483647";
    }
    description     
     "A positive integer.  Values in excess are precluded as
      unnecessary and prone to interoperability issues.";
  }

  typedef HelloRange {
    type int32 {
      range "1..65535";
    }
    description     
     "The range of intervals in seconds on which Hello messages
      are exchanged.";
  }

  typedef UpToMaxAge {
    type int32 {
      range "0..3600";
    }
    description     
     "The values in seconds that one might find or configure
      for variables bounded by the maximum age of an LSA.";
  }

  typedef DesignatedRouterPriority {
    type int32 {
      range "0..255";
    }
    description     
     "The range of values defined for the priority of a system
      for becoming the designated router.";
  }

  typedef TOSType {
    type int32 {
      range "0..30";
    }
    description     
     "Type of Service (TOS) is defined as a mapping to the IP
      Type of Service Flags as defined in the IP Forwarding
      Table MIB
      
          +-----+-----+-----+-----+-----+-----+-----+-----+
          |                 |                       |     |
          |   PRECEDENCE    |    TYPE OF SERVICE    |  0  |
          |                 |                       |     |
          +-----+-----+-----+-----+-----+-----+-----+-----+
      
                   IP TOS                IP TOS
              Field     Policy      Field     Policy
      
              Contents    Code      Contents    Code
              0 0 0 0  ==>   0      0 0 0 1  ==>   2
              0 0 1 0  ==>   4      0 0 1 1  ==>   6
              0 1 0 0  ==>   8      0 1 0 1  ==>  10
              0 1 1 0  ==>  12      0 1 1 1  ==>  14
              1 0 0 0  ==>  16      1 0 0 1  ==>  18
              1 0 1 0  ==>  20      1 0 1 1  ==>  22
              1 1 0 0  ==>  24      1 1 0 1  ==>  26
              1 1 1 0  ==>  28      1 1 1 1  ==>  30
      
       The remaining values are left for future definition.";
  }

  typedef OspfAuthenticationType {
    type enumeration {
      enum none           { value 0; }
      enum simplePassword { value 1; }
      enum md5            { value 2; }
    }
    description     
     "The authentication type.";
  }

  container ospf {


    /* XXX table comments here XXX */

    list AreaEntry {

      key "AreaId";
      description   
       "Information describing the configured parameters and
        cumulative statistics of one of the router's attached areas.
        The interfaces and virtual links are configured as part of
        these areas.  Area 0.0.0.0, by definition, is the backbone
        area.
        
        Information in this table is persistent and when this object
        is written the entity SHOULD save the change to non-volatile
        storage.";

      leaf AuthType {
        type ospf-mib:OspfAuthenticationType;
        config true;
        status obsolete;
        description 
         "The authentication type specified for an area.";
        reference   
         "OSPF Version 2, Appendix D Authentication";
      }

      leaf ImportAsExtern {
        type enumeration {
          enum importExternal   { value 1; }
          enum importNoExternal { value 2; }
          enum importNssa       { value 3; }
        }
        config true;
        description 
         "Indicates if an area is a stub area, NSSA, or standard
          area.  Type-5 AS-external LSAs and type-11 Opaque LSAs are
          not imported into stub areas or NSSAs.  NSSAs import
          AS-external data as type-7 LSAs";
        reference   
         "OSPF Version 2, Appendix C.2 Area parameters";
      }

      leaf AreaSummary {
        type enumeration {
          enum noAreaSummary   { value 1; }
          enum sendAreaSummary { value 2; }
        }
        config true;
        description 
         "The variable ospfAreaSummary controls the
          import of summary LSAs into stub and NSSA areas.
          It has no effect on other areas.
          
          If it is noAreaSummary, the router will not
          originate summary LSAs into the stub or NSSA area.
          It will rely entirely on its default route.
          
          If it is sendAreaSummary, the router will both
          summarize and propagate summary LSAs.";
      }

      leaf AreaNssaTranslatorRole {
        type enumeration {
          enum always    { value 1; }
          enum candidate { value 2; }
        }
        config true;
        description 
         "Indicates an NSSA border router's ability to
          perform NSSA translation of type-7 LSAs into
          type-5 LSAs.";
      }

      leaf AreaId {
        type ospf-mib:AreaID;
        config true;
        description
         "A 32-bit integer uniquely identifying an area.
          Area ID 0.0.0.0 is used for the OSPF backbone.";
        reference
         "OSPF Version 2, Appendix C.2 Area parameters";
      }

      leaf AreaNssaTranslatorStabilityInterval {
        type ospf-mib:PositiveInteger;
        units "seconds";
        config true;
		/*default "40";*/
        description 
         "The number of seconds after an elected translator
          determines its services are no longer required, that
          it should continue to perform its translation duties.";
      }

    }

list AreaEntryState {
	      key "AreaId";
      description   
       "Information describing the configured parameters and
        cumulative statistics of one of the router's attached areas.
        The interfaces and virtual links are configured as part of
        these areas.  Area 0.0.0.0, by definition, is the backbone
        area.
        
        Information in this table is persistent and when this object
        is written the entity SHOULD save the change to non-volatile
        storage.";
		
		leaf AreaId {
        type ospf-mib:AreaID;
        config true;
        description 
         "A 32-bit integer uniquely identifying an area.
          Area ID 0.0.0.0 is used for the OSPF backbone.";
        reference   
         "OSPF Version 2, Appendix C.2 Area parameters";
      }
		
	leaf SpfRuns {
        type yang:counter32;
        config false;
        description 
         "The number of times that the intra-area route
          table has been calculated using this area's
          link state database.  This is typically done
          using Dijkstra's algorithm.
          
          Discontinuities in the value of this counter can occur
          at re-initialization of the management system, and at other
          times as indicated by the value of ospfDiscontinuityTime.";
      }

      leaf AreaBdrRtrCount {
        type yang:gauge32;
        config false;
        description 
         "The total number of Area Border Routers reachable
          within this area.  This is initially zero and is
          calculated in each Shortest Path First (SPF) pass.";
      }

      leaf AsBdrRtrCount {
        type yang:gauge32;
        config false;
        description 
         "The total number of Autonomous System Border
          Routers reachable within this area.  This is
          initially zero and is calculated in each SPF
          pass.";
      }

      leaf AreaLsaCount {
        type yang:gauge32;
        config false;
        description 
         "The total number of link state advertisements
          in this area's link state database, excluding
          AS-external LSAs.";
      }
	      leaf AreaLsaCksumSum {
        type int32;
        config false;
        description 
         "The 32-bit sum of the link state
          advertisements' LS checksums contained in this
          area's link state database.  This sum excludes
          external (LS type-5) link state advertisements.
          The sum can be used to determine if there has
          been a change in a router's link state
          database, and to compare the link state database of
          two routers.  The value should be treated as unsigned
          when comparing two sums of checksums.";
      }
     leaf AreaNssaTranslatorState {
        type enumeration {
          enum enabled  { value 1; }
          enum elected  { value 2; }
          enum disabled { value 3; }
        }
        config false;
        description 
         "Indicates if and how an NSSA border router is
          performing NSSA translation of type-7 LSAs into type-5
          
          LSAs.  When this object is set to enabled, the NSSA Border
          router's OspfAreaNssaExtTranslatorRole has been set to
          always.  When this object is set to elected, a candidate
          NSSA Border router is Translating type-7 LSAs into type-5.
          When this object is set to disabled, a candidate NSSA
          border router is NOT translating type-7 LSAs into type-5.";
      }
	      leaf AreaNssaTranslatorEvents {
        type yang:counter32;
        config false;
        description 
         "Indicates the number of translator state changes
          that have occurred since the last boot-up.
          
          Discontinuities in the value of this counter can occur
          at re-initialization of the management system, and at other
          times as indicated by the value of ospfDiscontinuityTime.";
      }
	}
    /* XXX table comments here XXX */

    list StubAreaEntry {

      key "StubAreaId StubTOS";
      description   
       "The metric for a given Type of Service that
        will be advertised by a default Area Border
        Router into a stub area.
        
        Information in this table is persistent and when this object
        is written the entity SHOULD save the change to non-volatile
        storage.";
      reference     
       "OSPF Version 2, Appendix C.2, Area Parameters";


      leaf StubAreaId {
        type ospf-mib:AreaID;
        config true;
        description 
         "The 32-bit identifier for the stub area.  On
          creation, this can be derived from the
          instance.";
      }
	
	leaf StubTOS {
        type ospf-mib:TOSType;
        config true;
        description 
         "The Type of Service associated with the
          metric.  On creation, this can be derived from
          
          the instance.";
      }
 
      leaf StubMetric {
        type ospf-mib:BigMetric;
        config true;
        description 
         "The metric value applied at the indicated Type
          of Service.  By default, this equals the least
          metric at the Type of Service among the
          interfaces to other areas.";
      }


      leaf StubMetricType {
        type enumeration {
          enum ospfMetric     { value 1; }
          enum comparableCost { value 2; }
          enum nonComparable  { value 3; }
        }
        config true;
        description 
         "This variable displays the type of metric
          advertised as a default route.";
      }
    }
 
    /* XXX table comments here XXX */

  list LsdbEntryState {
	     key "LsdbAreaId LsdbType LsdbLsid 
           LsdbRouterId";
      description   
       "A single link state advertisement.";
	
	     leaf LsdbAreaId {
        type ospf-mib:AreaID;
        config true;
        description 
         "The 32-bit identifier of the area from which
          the LSA was received.";
        reference   
         "OSPF Version 2, Appendix C.2 Area parameters";
      }

      leaf LsdbType {
        type enumeration {
          enum routerLink       { value 1; }
          enum networkLink      { value 2; }
          enum summaryLink      { value 3; }
          enum asSummaryLink    { value 4; }
          enum asExternalLink   { value 5; }
          enum multicastLink    { value 6; }
          enum nssaExternalLink { value 7; }
          enum areaOpaqueLink   { value 10; }
        }
        config true;
        description 
         "The type of the link state advertisement.
          Each link state type has a separate advertisement
          format.
          
          Note: External link state advertisements are permitted
          for backward compatibility, but should be displayed
          in the AsLsdbTable rather than here.";
        reference   
         "OSPF Version 2, Appendix A.4.1 The Link State
          Advertisement header";
      }

      leaf LsdbLsid {
        type inet:ipv4-address;
        config true;
        description 
         "The Link State ID is an LS Type Specific field
          containing either a Router ID or an IP address;
          it identifies the piece of the routing domain
          that is being described by the advertisement.";
        reference   
         "OSPF Version 2, Section 12.1.4 Link State ID";
      }

      leaf LsdbRouterId {
        type ospf-mib:RouterID;
        config true;
        description 
         "The 32-bit number that uniquely identifies the
          originating router in the Autonomous System.";
        reference   
         "OSPF Version 2, Appendix C.1 Global parameters";
      }
	
	   leaf LsdbSequence {
        type int32;
        config false;
        description 
         "The sequence number field is a signed 32-bit
          integer.  It starts with the value '80000001'h,
          or -'7FFFFFFF'h, and increments until '7FFFFFFF'h.
          Thus, a typical sequence number will be very negative.
          It is used to detect old and duplicate Link State
          Advertisements.  The space of sequence numbers is linearly
          ordered.  The larger the sequence number, the more recent
          the advertisement.";
        reference   
         "OSPF Version 2, Section 12.1.6 LS sequence
          number";
      }
	  leaf LsdbAge {
        type int32;
        units "seconds";
        config false;
        description 
         "This field is the age of the link state advertisement
          in seconds.";
        reference   
         "OSPF Version 2, Section 12.1.1 LS age";
      }

      leaf LsdbChecksum {
        type int32;
        config false;
        description 
         "This field is the checksum of the complete contents of
          the advertisement, excepting the age field.  The age field
          is excepted so that an advertisement's age can be
          incremented without updating the checksum.  The checksum
          used is the same that is used for ISO connectionless
          
          datagrams; it is commonly referred to as the
          Fletcher checksum.";
        reference   
         "OSPF Version 2, Section 12.1.7 LS checksum";
      }
	
      leaf LsdbAdvertisement {
        type binary {
          length "1..65535";
        }
        config false;
        description 
         "The entire link state advertisement, including
          its header.
          
          Note that for variable length LSAs, SNMP agents
          may not be able to return the largest string size.";
        reference   
         "OSPF Version 2, Section 12 Link State Advertisements";
      }
	}


    /* XXX table comments here XXX */

    list IfEntry {

      key "IfIpAddress AddressLessIf";
      description   
       "The OSPF interface entry describes one interface
        from the viewpoint of OSPF.
        
        Information in this table is persistent and when this object
        is written the entity SHOULD save the change to non-volatile
        storage.";


      leaf IfIpAddress {
        type inet:ipv4-address;
        config true;
        description 
         "The IP address of this OSPF interface.";
      }

      leaf AddressLessIf {
        type InterfaceIndexOrZero;
        config true;
        description 
         "For the purpose of easing the instancing of
          addressed and addressless interfaces; this
          variable takes the value 0 on interfaces with
          IP addresses and the corresponding value of
          ifIndex for interfaces having no IP address.";
      }

      leaf IfAreaId {
        type ospf-mib:AreaID;
        config true;
		/*default "0.0.0.0";*/
        description 
         "A 32-bit integer uniquely identifying the area
          to which the interface connects.  Area ID
          0.0.0.0 is used for the OSPF backbone.";
      }

      leaf IfType {
        type enumeration {
          enum broadcast         { value 1; }
          enum nbma              { value 2; }
          enum pointToPoint      { value 3; }
          enum pointToMultipoint { value 5; }
        }
        config true;
        description 
         "The OSPF interface type.
          By way of a default, this field may be intuited
          from the corresponding value of ifType.
          Broadcast LANs, such as Ethernet and IEEE 802.5,
          take the value 'broadcast', X.25 and similar
          technologies take the value 'nbma', and links
          that are definitively point to point take the
          value 'pointToPoint'.";
      }

      leaf IfAdminStat {
        type ospf-mib:Status;
        config true;
        description 
         "The OSPF interface's administrative status.
          The value formed on the interface, and the interface
          will be advertised as an internal route to some area.
          The value 'disabled' denotes that the interface is
          external to OSPF.";
      }

      leaf IfRtrPriority {
        type ospf-mib:DesignatedRouterPriority;
        config true;
		/*default "1";*/
        description 
         "The priority of this interface.  Used in
          multi-access networks, this field is used in
          the designated router election algorithm.  The
          value 0 signifies that the router is not eligible
          to become the designated router on this particular
          network.  In the event of a tie in this value,
          routers will use their Router ID as a tie breaker.";
      }

      leaf IfTransitDelay {
        type ospf-mib:UpToMaxAge;
        units "seconds";
        config true;
		/*default "1";*/
        description 
         "The estimated number of seconds it takes to
          transmit a link state update packet over this
          interface.  Note that the minimal value SHOULD be
          1 second.";
      }

      leaf IfRetransInterval {
        type ospf-mib:UpToMaxAge;
        units "seconds";
        config true;
		/*default "5";*/
        description 
         "The number of seconds between link state advertisement
          retransmissions, for adjacencies belonging to this
          interface.  This value is also used when retransmitting
          
          database description and Link State request packets.
          Note that minimal value SHOULD be 1 second.";
      }

      leaf IfHelloInterval {
        type ospf-mib:HelloRange;
        units "seconds";
        config true;
		/*default "10";*/
        description 
         "The length of time, in seconds, between the Hello packets
          that the router sends on the interface.  This value must be
          the same for all routers attached to a common network.";
      }

      leaf IfRtrDeadInterval {
        type ospf-mib:PositiveInteger;
        units "seconds";
        config true;
		/*default "40";*/
        description 
         "The number of seconds that a router's Hello packets have
          not been seen before its neighbors declare the router down.
          This should be some multiple of the Hello interval.  This
          value must be the same for all routers attached to a common
          network.";
      }

      leaf IfPollInterval {
        type ospf-mib:PositiveInteger;
        units "seconds";
        config true;
		/*default "120";*/
        description 
         "The larger time interval, in seconds, between the Hello
          packets sent to an inactive non-broadcast multi-access
          neighbor.";
      }

 

      leaf IfAuthKey {
        type binary {
          length "0..256";
        }
        config true;
        description 
         "The cleartext password used as an OSPF
          authentication key when simplePassword security
          is enabled.  This object does not access any OSPF
          cryptogaphic (e.g., MD5) authentication key under
          any circumstance.
          
          If the key length is shorter than 8 octets, the
          agent will left adjust and zero fill to 8 octets.
          
          Unauthenticated interfaces need no authentication
          key, and simple password authentication cannot use
          a key of more than 8 octets.
          
          Note that the use of simplePassword authentication
          is NOT recommended when there is concern regarding
          attack upon the OSPF system.  SimplePassword
          authentication is only sufficient to protect against
          accidental misconfigurations because it re-uses
          cleartext passwords [RFC1704].
          
          When read, ospfIfAuthKey always returns an octet
          string of length zero.";
        reference   
         "OSPF Version 2, Section 9 The Interface Data
          Structure";
      }


      leaf IfMulticastForwarding {
        type enumeration {
          enum blocked   { value 1; }
          enum multicast { value 2; }
          enum unicast   { value 3; }
        }
        config true;
        description 
         "The way multicasts should be forwarded on this
          interface: not forwarded, forwarded as data
          link multicasts, or forwarded as data link
          unicasts.  Data link multicasting is not
          meaningful on point-to-point and NBMA interfaces,
          and setting ospfMulticastForwarding to 0 effectively
          disables all multicast forwarding.";
      }

      leaf IfDemand {
        type boolean;
        config true;
        /*default "false";*/
        description 
         "Indicates whether Demand OSPF procedures (hello
          suppression to FULL neighbors and setting the
          DoNotAge flag on propagated LSAs) should be
          performed on this interface.";
      }

      leaf IfAuthType {
        type ospf-mib:OspfAuthenticationType;
        config true;
        description 
         "The authentication type specified for an interface.
          
          Note that this object can be used to engage
          in significant attacks against an OSPF router.";
        reference   
         "OSPF Version 2, Appendix D Authentication";
      }
    }
	
	
    list IfEntryState {
      key "IfIpAddress AddressLessIf";
      description   
       "The OSPF interface entry describes one interface
        from the viewpoint of OSPF.
        
        Information in this table is persistent and when this object
        is written the entity SHOULD save the change to non-volatile
        storage.";

      leaf IfIpAddress {
        type inet:ipv4-address;
        config true;
        description 
         "The IP address of this OSPF interface.";
      }

      leaf AddressLessIf {
        type InterfaceIndexOrZero;
        config true;
        description 
         "For the purpose of easing the instancing of
          addressed and addressless interfaces; this
          variable takes the value 0 on interfaces with
          IP addresses and the corresponding value of
          ifIndex for interfaces having no IP address.";
      }

       leaf IfState {
        type enumeration {
          enum down                   { value 1; }
          enum loopback               { value 2; }
          enum waiting                { value 3; }
          enum pointToPoint           { value 4; }
          enum designatedRouter       { value 5; }
          enum backupDesignatedRouter { value 6; }
          enum otherDesignatedRouter  { value 7; }
        }
        config false;
        description 
         "The OSPF Interface State.";
      }

      leaf IfDesignatedRouter {
        type inet:ipv4-address;
        config false;
        /*default "0.0.0.0";*/
        description 
         "The IP address of the designated router.";
      }

      leaf IfBackupDesignatedRouter {
        type inet:ipv4-address;
        config false;
        description 
         "The IP address of the backup designated
          router.";
      }

      leaf IfEvents {
        type yang:counter32;
        config false;
        description 
         "The number of times this OSPF interface has
          changed its state or an error has occurred.
          
          Discontinuities in the value of this counter can occur
          at re-initialization of the management system, and at other
          times as indicated by the value of ospfDiscontinuityTime.";
      }
	      leaf IfLsaCount {
        type yang:gauge32;
        config false;
        description 
         "The total number of link-local link state advertisements
          in this interface's link-local link state database.";
      }
	     leaf IfLsaCksumSum {
        type uint32;
        config false;
        description 
         "The 32-bit unsigned sum of the Link State
          Advertisements' LS checksums contained in this
          interface's link-local link state database.
          The sum can be used to determine if there has
          been a change in the interface's link state
          database and to compare the interface link state
          database of routers attached to the same subnet.";
      }

      leaf IfDesignatedRouterId {
        type ospf-mib:RouterID;
        config false;
        description 
         "The Router ID of the designated router.";
      }

      leaf IfBackupDesignatedRouterId {
        type ospf-mib:RouterID;
        config false;
        description 
         "The Router ID of the backup designated router.";
      }
	}


    /* XXX table comments here XXX */

    list IfMetricEntry {

      key "IfMetricIpAddress IfMetricAddressLessIf 
           IfMetricTOS";
      description   
       "A particular TOS metric for a non-virtual interface
        identified by the interface index.
        
        Information in this table is persistent and when this object
        is written the entity SHOULD save the change to non-volatile
        storage.";
      reference     
       "OSPF Version 2, Appendix C.3 Router interface
        parameters";


      leaf IfMetricIpAddress {
        type inet:ipv4-address;
        config true;
        description 
         "The IP address of this OSPF interface.  On row
          creation, this can be derived from the instance.";
      }

      leaf IfMetricAddressLessIf {
        type InterfaceIndexOrZero;
        config true;
        description 
         "For the purpose of easing the instancing of
          addressed and addressless interfaces; this
          variable takes the value 0 on interfaces with
          IP addresses and the value of ifIndex for
          interfaces having no IP address.  On row
          creation, this can be derived from the instance.";
      }

      leaf IfMetricTOS {
        type ospf-mib:TOSType;
        config true;
        description 
         "The Type of Service metric being referenced.
          On row creation, this can be derived from the
          instance.";
      }

      leaf IfMetricValue {
        type ospf-mib:Metric;
        config true;
        description 
         "The metric of using this Type of Service on
          this interface.  The default value of the TOS 0
          metric is 10^8 / ifSpeed.";
      }

    }



    /* XXX table comments here XXX */

    list VirtIfEntry {

      key "VirtIfAreaId VirtIfNeighbor";
      description   
       "Information about a single virtual interface.
        
        Information in this table is persistent and when this object
        is written the entity SHOULD save the change to non-volatile
        storage.";


      leaf VirtIfAreaId {
        type ospf-mib:AreaID;
        config true;
        description 
         "The transit area that the virtual link
          traverses.  By definition, this is not 0.0.0.0.";
      }

      leaf VirtIfNeighbor {
        type ospf-mib:RouterID;
        config true;
        description 
         "The Router ID of the virtual neighbor.";
      }

      leaf VirtIfTransitDelay {
        type ospf-mib:UpToMaxAge;
        units "seconds";
        config true;
		/*default "1";*/
        description 
         "The estimated number of seconds it takes to
          transmit a Link State update packet over this
          interface.  Note that the minimal value SHOULD be
          1 second.";
      }

      leaf VirtIfRetransInterval {
        type ospf-mib:UpToMaxAge;
        units "seconds";
        config true;
		/*default "5";*/
        description 
         "The number of seconds between link state
          avertisement retransmissions, for adjacencies
          belonging to this interface.  This value is
          also used when retransmitting database
          description and Link State request packets.  This
          value should be well over the expected
          round-trip time.  Note that the minimal value SHOULD be
          1 second.";
      }

      leaf VirtIfHelloInterval {
        type ospf-mib:HelloRange;
        units "seconds";
        config true;
		/*default "10";*/
        description 
         "The length of time, in seconds, between the
          Hello packets that the router sends on the
          interface.  This value must be the same for the
          virtual neighbor.";
      }

      leaf VirtIfRtrDeadInterval {
        type ospf-mib:PositiveInteger;
        units "seconds";
        config true;
		/*default "60";*/
        description 
         "The number of seconds that a router's Hello
          packets have not been seen before its
          neighbors declare the router down.  This should be
          some multiple of the Hello interval.  This
          value must be the same for the virtual neighbor.";
      }

      leaf VirtIfAuthKey {
        type binary {
          length "0..256";
        }
        config true;
        description 
         "The cleartext password used as an OSPF
          authentication key when simplePassword security
          is enabled.  This object does not access any OSPF
          cryptogaphic (e.g., MD5) authentication key under
          any circumstance.
          
          If the key length is shorter than 8 octets, the
          agent will left adjust and zero fill to 8 octets.
          
          Unauthenticated interfaces need no authentication
          key, and simple password authentication cannot use
          a key of more than 8 octets.
          
          Note that the use of simplePassword authentication
          is NOT recommended when there is concern regarding
          attack upon the OSPF system.  SimplePassword
          authentication is only sufficient to protect against
          accidental misconfigurations because it re-uses
          cleartext passwords.  [RFC1704]
          
          When read, ospfIfAuthKey always returns an octet
          string of length zero.";
        reference   
         "OSPF Version 2, Section 9 The Interface Data
          Structure";
      }

      leaf VirtIfAuthType {
        type ospf-mib:OspfAuthenticationType;
        config true;
        description 
         "The authentication type specified for a virtual interface.
          
          Note that this object can be used to engage
          in significant attacks against an OSPF router.";
        reference   
         "OSPF Version 2, Appendix E Authentication";
      }
    }


    /* XXX table comments here XXX */

list NbrEntryState {
	  key "NbrIpAddr NbrAddressLessIndex";
      description   
       "The information regarding a single neighbor.
        
        Information in this table is persistent and when this object
        is written the entity SHOULD save the change to non-volatile
        
        storage.";
      reference     
       "OSPF Version 2, Section 10 The Neighbor Data
        Structure";
		
	 leaf NbrIpAddr {
        type inet:ipv4-address;
        config true;
        description 
         "The IP address this neighbor is using in its
          IP source address.  Note that, on addressless
          links, this will not be 0.0.0.0 but the
          
          address of another of the neighbor's interfaces.";
      }

      leaf NbrAddressLessIndex {
        type InterfaceIndexOrZero;
        config true;
        description 
         "On an interface having an IP address, zero.
          On addressless interfaces, the corresponding
          value of ifIndex in the Internet Standard MIB.
          On row creation, this can be derived from the
          instance.";
      }
	
	    leaf NbrRtrId {
        type ospf-mib:RouterID;
        config false;
	/*default "0.0.0.0";*/
        description 
         "A 32-bit integer (represented as a type
          IpAddress) uniquely identifying the neighboring
          router in the Autonomous System.";
      }

      leaf NbrOptions {
        type int32;
        config false;
		/*default "0";*/
        description 
         "A bit mask corresponding to the neighbor's
          options field.
          
          Bit 0, if set, indicates that the system will
          operate on Type of Service metrics other than
          TOS 0.  If zero, the neighbor will ignore all
          metrics except the TOS 0 metric.
          
          Bit 1, if set, indicates that the associated
          area accepts and operates on external
          information; if zero, it is a stub area.
          
          Bit 2, if set, indicates that the system is
          capable of routing IP multicast datagrams, that is
          that it implements the multicast extensions to
          OSPF.
          
          Bit 3, if set, indicates that the associated
          area is an NSSA.  These areas are capable of
          carrying type-7 external advertisements, which
          are translated into type-5 external advertisements
          at NSSA borders.";
        reference   
         "OSPF Version 2, Section 12.1.2 Options";
      }
	      leaf NbrState {
        type enumeration {
          enum down          { value 1; }
          enum attempt       { value 2; }
          enum init          { value 3; }
          enum twoWay        { value 4; }
          enum exchangeStart { value 5; }
          enum exchange      { value 6; }
          enum loading       { value 7; }
          enum full          { value 8; }
        }
        config false;
        description 
         "The state of the relationship with this neighbor.";
        reference   
         "OSPF Version 2, Section 10.1 Neighbor States";
      }

      leaf NbrEvents {
        type yang:counter32;
        config false;
        description 
         "The number of times this neighbor relationship
          has changed state or an error has occurred.
          
          Discontinuities in the value of this counter can occur
          at re-initialization of the management system, and at other
          times as indicated by the value of ospfDiscontinuityTime.";
      }

      leaf NbrLsRetransQLen {
        type yang:gauge32;
        config false;
        description 
         "The current length of the retransmission
          queue.";
      }
	      leaf NbmaNbrPermanence {
        type enumeration {
          enum dynamic   { value 1; }
          enum permanent { value 2; }
        }
        config false;
        description 
         "This variable displays the status of the entry;
          'dynamic' and 'permanent' refer to how the neighbor
          became known.";
      }

      leaf NbrHelloSuppressed {
        type boolean;
        config false;
        description 
         "Indicates whether Hellos are being suppressed
          to the neighbor.";
      }

      leaf NbrRestartHelperStatus {
        type enumeration {
          enum notHelping { value 1; }
          enum helping    { value 2; }
        }
        config false;
        description 
         "Indicates whether the router is acting
          as a graceful restart helper for the neighbor.";
      }

      leaf NbrRestartHelperAge {
        type uint32;
        units "seconds";
        config false;
        description 
         "Remaining time in current OSPF graceful restart
          interval, if the router is acting as a restart
          helper for the neighbor.";
      }

      leaf NbrRestartHelperExitReason {
        type enumeration {
          enum none            { value 1; }
          enum inProgress      { value 2; }
          enum completed       { value 3; }
          enum timedOut        { value 4; }
          enum topologyChanged { value 5; }
        }
        config false;
        description 
         "Describes the outcome of the last attempt at acting
          as a graceful restart helper for the neighbor.";
      }
	}

    /* XXX table comments here XXX */

    list VirtNbrEntryState {

      key "VirtNbrArea VirtNbrRtrId";
      description   
       "Virtual neighbor information.";


      leaf VirtNbrArea {
        type ospf-mib:AreaID;
        config true;
        description 
         "The Transit Area Identifier.";
      }

      leaf VirtNbrRtrId {
        type ospf-mib:RouterID;
        config true;
        description 
         "A 32-bit integer uniquely identifying the
          neighboring router in the Autonomous System.";
      }

      leaf VirtNbrIpAddr {
        type inet:ipv4-address;
        config false;
        description 
         "The IP address this virtual neighbor is using.";
      }

      leaf VirtNbrOptions {
        type int32;
        config false;
		/*default "0";*/
        description 
         "A bit mask corresponding to the neighbor's
          options field.
          
          Bit 1, if set, indicates that the system will
          operate on Type of Service metrics other than
          TOS 0.  If zero, the neighbor will ignore all
          metrics except the TOS 0 metric.
          
          Bit 2, if set, indicates that the system is
          network multicast capable, i.e., that it
          implements OSPF multicast routing.";
      }

      leaf VirtNbrState {
        type enumeration {
          enum down          { value 1; }
          enum attempt       { value 2; }
          enum init          { value 3; }
          enum twoWay        { value 4; }
          enum exchangeStart { value 5; }
          enum exchange      { value 6; }
          enum loading       { value 7; }
          enum full          { value 8; }
        }
        config false;
        description 
         "The state of the virtual neighbor relationship.";
      }

      leaf VirtNbrEvents {
        type yang:counter32;
        config false;
        description 
         "The number of times this virtual link has
          changed its state or an error has occurred.
          
          Discontinuities in the value of this counter can occur
          at re-initialization of the management system, and at other
          times as indicated by the value of ospfDiscontinuityTime.";
      }

      leaf VirtNbrLsRetransQLen {
        type yang:gauge32;
        config false;
        description 
         "The current length of the retransmission
          queue.";
      }

      leaf VirtNbrHelloSuppressed {
        type boolean;
        config false;
        description 
         "Indicates whether Hellos are being suppressed
          to the neighbor.";
      }

      leaf VirtNbrRestartHelperStatus {
        type enumeration {
          enum notHelping { value 1; }
          enum helping    { value 2; }
        }
        config false;
        description 
         "Indicates whether the router is acting
          as a graceful restart helper for the neighbor.";
      }

      leaf VirtNbrRestartHelperAge {
        type uint32;
        units "seconds";
        config false;
        description 
         "Remaining time in current OSPF graceful restart
          interval, if the router is acting as a restart
          helper for the neighbor.";
      }

      leaf VirtNbrRestartHelperExitReason {
        type enumeration {
          enum none            { value 1; }
          enum inProgress      { value 2; }
          enum completed       { value 3; }
          enum timedOut        { value 4; }
          enum topologyChanged { value 5; }
        }
        config false;
        description 
         "Describes the outcome of the last attempt at acting
          as a graceful restart helper for the neighbor.";
      }
    }


    /* XXX table comments here XXX */

     list VirtLocalLsdbEntryState {
	key "VirtLocalLsdbTransitArea 
           VirtLocalLsdbNeighbor VirtLocalLsdbType 
           VirtLocalLsdbLsid VirtLocalLsdbRouterId";
      description   
       "A single link state advertisement.";

    leaf VirtLocalLsdbTransitArea {
        type ospf-mib:AreaID;
        config true;
        description 
         "The transit area that the virtual link
          traverses.  By definition, this is not 0.0.0.0.";
        reference   
         "OSPF Version 2, Appendix C.3 Interface parameters";
      }

      leaf VirtLocalLsdbNeighbor {
        type ospf-mib:RouterID;
        config true;
        description 
         "The Router ID of the virtual neighbor.";
        reference   
         "OSPF Version 2, Appendix C.3 Interface parameters";
      }

      leaf VirtLocalLsdbType {
        type enumeration {
          enum localOpaqueLink { value 9; }
        }
        config true;
        description 
         "The type of the link state advertisement.
          Each link state type has a separate
          advertisement format.";
        reference   
         "OSPF Version 2, Appendix A.4.1 The Link State
          Advertisement header";
      }

      leaf VirtLocalLsdbLsid {
        type inet:ipv4-address;
        config true;
        description 
         "The Link State ID is an LS Type Specific field
          containing a 32-bit identifier in IP address format;
          it identifies the piece of the routing domain
          that is being described by the advertisement.";
        reference   
         "OSPF Version 2, Section 12.1.4 Link State ID";
      }

      leaf VirtLocalLsdbRouterId {
        type ospf-mib:RouterID;
        config true;
        description 
         "The 32-bit number that uniquely identifies the
          originating router in the Autonomous System.";
        reference   
         "OSPF Version 2, Appendix C.1 Global parameters";
      }
	
     leaf VirtLocalLsdbSequence {
        type int32;
        config false;
        description 
         "The sequence number field is a signed 32-bit
          integer.  It starts with the value '80000001'h,
          or -'7FFFFFFF'h, and increments until '7FFFFFFF'h.
          Thus, a typical sequence number will be very negative.
          It is used to detect old and duplicate link state
          advertisements.  The space of sequence numbers is linearly
          ordered.  The larger the sequence number, the more recent
          the advertisement.";
        reference   
         "OSPF Version 2, Section 12.1.6 LS sequence
          number";
      }

      leaf VirtLocalLsdbAge {
        type int32;
        units "seconds";
        config false;
        description 
         "This field is the age of the link state
          advertisement in seconds.";
        reference   
         "OSPF Version 2, Section 12.1.1 LS age";
      }

      leaf VirtLocalLsdbChecksum {
        type int32;
        config false;
        description 
         "This field is the checksum of the complete
          contents of the advertisement, excepting the
          age field.  The age field is excepted so that
          
          an advertisement's age can be incremented
          without updating the checksum.  The checksum
          used is the same that is used for ISO
          connectionless datagrams; it is commonly
          referred to as the Fletcher checksum.";
        reference   
         "OSPF Version 2, Section 12.1.7 LS checksum";
      }

      leaf VirtLocalLsdbAdvertisement {
        type binary {
          length "1..65535";
        }
        config false;
        description 
         "The entire link state advertisement, including
          its header.";
        reference   
         "OSPF Version 2, Section 12 Link State
          Advertisements.
          
          Note that for variable length LSAs, SNMP agents
          may not be able to return the largest string size.";
      }
	}

list Global {
      key RouterId;
    leaf RouterId {
      type ospf-mib:RouterID;
      config true;
      description   
       "A 32-bit integer uniquely identifying the
        router in the Autonomous System.
        By convention, to ensure uniqueness, this
        should default to the value of one of the
        router's IP interface addresses.
        
        This object is persistent and when written
        the entity SHOULD save the change to non-volatile storage.";
      reference     
       "OSPF Version 2, C.1 Global parameters";
    }

    leaf AdminStat {
      type ospf-mib:Status;
      config true;
      description   
       "The administrative status of OSPF in the
        router.  The value 'enabled' denotes that the
        OSPF Process is active on at least one interface;
        'disabled' disables it on all interfaces.
        
        This object is persistent and when written
        the entity SHOULD save the change to non-volatile storage.";
    }

     leaf ASBdrRtrStatus {
      type boolean;
      config true;
      description   
       "A flag to note whether this router is configured as
        an Autonomous System Border Router.
        
        This object is persistent and when written the
        entity SHOULD save the change to non-volatile storage.";
      reference     
       "OSPF Version 2, Section 3.3 Classification of
        routers";
    }

 
    leaf TOSSupport {
      type boolean;
      config true;
      description   
       "The router's support for type-of-service routing.
        
        This object is persistent and when written
        the entity SHOULD save the change to non-volatile
        storage.";
      reference     
       "OSPF Version 2, Appendix F.1.2 Optional TOS
        support";
    }

 
    leaf ExtLsdbLimit {
      type int32 {
        range "-1..2147483647";
      }
      config true;
      description   
       "The maximum number of non-default
        AS-external LSAs entries that can be stored in the
        link state database.  If the value is -1, then
        there is no limit.
        
        When the number of non-default AS-external LSAs
        in a router's link state database reaches
        ospfExtLsdbLimit, the router enters
        overflow state.  The router never holds more than
        ospfExtLsdbLimit non-default AS-external LSAs
        in its database.  OspfExtLsdbLimit MUST be set
        identically in all routers attached to the OSPF
        backbone and/or any regular OSPF area (i.e.,
        OSPF stub areas and NSSAs are excluded).
        
        This object is persistent and when written
        the entity SHOULD save the change to non-volatile
        storage.";
    }

    leaf MulticastExtensions {
      type int32;
      config true;
      description   
       "A bit mask indicating whether the router is
        forwarding IP multicast (Class D) datagrams
        based on the algorithms defined in the
        multicast extensions to OSPF.
        
        Bit 0, if set, indicates that the router can
        
        forward IP multicast datagrams in the router's
        directly attached areas (called intra-area
        multicast routing).
        
        Bit 1, if set, indicates that the router can
        forward IP multicast datagrams between OSPF
        areas (called inter-area multicast routing).
        
        Bit 2, if set, indicates that the router can
        forward IP multicast datagrams between
        Autonomous Systems (called inter-AS multicast
        routing).
        
        Only certain combinations of bit settings are
        allowed, namely: 0 (no multicast forwarding is
        enabled), 1 (intra-area multicasting only), 3
        (intra-area and inter-area multicasting), 5
        (intra-area and inter-AS multicasting), and 7
        (multicasting everywhere).  By default, no
        multicast forwarding is enabled.
        
        This object is persistent and when written
        the entity SHOULD save the change to non-volatile
        storage.";
    }

    leaf ExitOverflowInterval {
      type ospf-mib:PositiveInteger;
      config true;
      description   
       "The number of seconds that, after entering
        OverflowState, a router will attempt to leave
        OverflowState.  This allows the router to again
        originate non-default AS-external LSAs.  When
        set to 0, the router will not leave
        overflow state until restarted.
        
        This object is persistent and when written
        the entity SHOULD save the change to non-volatile
        storage.";
    }

    leaf DemandExtensions {
      type boolean;
      config true;
      description   
       "The router's support for demand routing.
        This object is persistent and when written
        the entity SHOULD save the change to non-volatile
        storage.";
      reference     
       "Extending OSPF to Support Demand Circuits";
    }

    leaf RFC1583Compatibility {
      type boolean;
      config true;
      description   
       "Indicates metrics used to choose among multiple
        AS-external LSAs.  When RFC1583Compatibility is set to
        enabled, only cost will be used when choosing among
        multiple AS-external LSAs advertising the same
        destination.  When RFC1583Compatibility is set to
        disabled, preference will be driven first by type of
        path using cost only to break ties.
        
        This object is persistent and when written
        the entity SHOULD save the change to non-volatile
        storage.";
      reference     
       "OSPF Version 2, Section 16.4.1 External path
        preferences";
    }

 
    leaf ReferenceBandwidth {
      type uint32;
      units "kilobits per second";
      config true;
      description   
       "Reference bandwidth in kilobits/second for
        
        calculating default interface metrics.  The
        default value is 100,000 KBPS (100 MBPS).
        
        This object is persistent and when written
        the entity SHOULD save the change to non-volatile
        storage.";
    }

    leaf RestartSupport {
      type enumeration {
        enum none                { value 1; }
        enum plannedOnly         { value 2; }
        enum plannedAndUnplanned { value 3; }
      }
      config true;
      description   
       "The router's support for OSPF graceful restart.
        Options include: no restart support, only planned
        restarts, or both planned and unplanned restarts.
        
        This object is persistent and when written
        the entity SHOULD save the change to non-volatile
        storage.";
    }

    leaf RestartInterval {
      type int32 {
        range "1..1800";
      }
      units "seconds";
      config true;
      description   
       "Configured OSPF graceful restart timeout interval.
        
        This object is persistent and when written
        the entity SHOULD save the change to non-volatile
        storage.";
    }

    leaf RestartStrictLsaChecking {
      type boolean;
      config true;
      description   
       "Indicates if strict LSA checking is enabled for
        graceful restart.
        
        This object is persistent and when written
        the entity SHOULD save the change to non-volatile
        
        storage.";
    }

 
    leaf StubRouterAdvertisement {
      type enumeration {
        enum doNotAdvertise { value 1; }
        enum advertise      { value 2; }
      }
      config true;
      description   
       "This object controls the advertisement of
        stub router LSAs by the router.  The value
        doNotAdvertise will result in the advertisement
        of a standard router LSA and is the default value.
        
        This object is persistent and when written
        the entity SHOULD save the change to non-volatile
        storage.";
    }

  }

list GlobalState {
      key RouterId;
    leaf RouterId {
      type ospf-mib:RouterID;
      config true;
      description   
       "A 32-bit integer uniquely identifying the
        router in the Autonomous System.
        By convention, to ensure uniqueness, this
        should default to the value of one of the
        router's IP interface addresses.
        
        This object is persistent and when written
        the entity SHOULD save the change to non-volatile storage.";
      reference     
       "OSPF Version 2, C.1 Global parameters";
    }
	
	   leaf VersionNumber {
      type enumeration {
        enum version2 { value 2; }
      }
      config false;
      description   
       "The current version number of the OSPF protocol is 2.";
      reference     
       "OSPF Version 2, Title";
    }


    leaf AreaBdrRtrStatus {
      type boolean;
      config false;
      description   
       "A flag to note whether this router is an Area
        Border Router.";
      reference     
       "OSPF Version 2, Section 3 Splitting the AS into
        Areas";
    }

   leaf ExternLsaCount {
      type yang:gauge32;
      config false;
      description   
       "The number of external (LS type-5) link state
        advertisements in the link state database.";
      reference     
       "OSPF Version 2, Appendix A.4.5 AS external link
        advertisements";
    }

    leaf ExternLsaCksumSum {
      type int32;
      config false;
      description   
       "The 32-bit sum of the LS checksums of
        the external link state advertisements
        contained in the link state database.  This sum
        can be used to determine if there has been a
        change in a router's link state database and
        to compare the link state database of two
        routers.  The value should be treated as unsigned
        when comparing two sums of checksums.";
    }


   leaf OriginateNewLsas {
      type yang:counter32;
      config false;
      description   
       "The number of new link state advertisements
        that have been originated.  This number is
        incremented each time the router originates a new
        LSA.
        
        Discontinuities in the value of this counter can
        occur at re-initialization of the management system,
        and at other times as indicated by the value of
        spfDiscontinuityTime.";
    }

    leaf RxNewLsas {
      type yang:counter32;
      config false;
      description   
       "The number of link state advertisements received
        that are determined to be new instantiations.
        This number does not include newer instantiations
        of self-originated link state advertisements.
        
        Discontinuities in the value of this counter can
        occur at re-initialization of the management system,
        and at other times as indicated by the value of
        ospfDiscontinuityTime.";
    }

   leaf OpaqueLsaSupport {
      type boolean;
      config false;
      description   
       "The router's support for Opaque LSA types.";
      reference     
       "The OSPF Opaque LSA Option";
    }
   leaf RestartStatus {
      type enumeration {
        enum notRestarting    { value 1; }
        enum plannedRestart   { value 2; }
        enum unplannedRestart { value 3; }
      }
      config false;
      description   
       "Current status of OSPF graceful restart.";
    }

    leaf RestartAge {
      type uint32;
      units "seconds";
      config false;
      description   
       "Remaining time in current OSPF graceful restart
        interval.";
    }

    leaf RestartExitReason {
      type enumeration {
        enum none            { value 1; }
        enum inProgress      { value 2; }
        enum completed       { value 3; }
        enum timedOut        { value 4; }
        enum topologyChanged { value 5; }
      }
      config false;
      description   
       "Describes the outcome of the last attempt at a
        graceful restart.  If the value is 'none', no restart
        has yet been attempted.  If the value is 'inProgress',
        a restart attempt is currently underway.";
    }

    leaf AsLsaCount {
      type yang:gauge32;
      config false;
      description   
       "The number of AS-scope link state
        advertisements in the AS-scope link state database.";
    }

    leaf AsLsaCksumSum {
      type uint32;
      config false;
      description   
       "The 32-bit unsigned sum of the LS checksums of
        the AS link state advertisements contained in the AS-scope
        link state database.  This sum can be used to determine
        if there has been a change in a router's AS-scope link
        state database, and to compare the AS-scope link state
        database of two routers.";
    }

    leaf StubRouterSupport {
      type boolean;
      config false;
      description   
       "The router's support for stub router functionality.";
      reference     
       "OSPF Stub Router Advertisement";
    }

 leaf DiscontinuityTime {
      type yang:timestamp;
      config false;
      description   
       "The value of sysUpTime on the most recent occasion
        at which any one of this MIB's counters suffered
        a discontinuity.
        
        If no such discontinuities have occurred since the last
        re-initialization of the local management subsystem,
        then this object contains a zero value.";
    }
	
	}

}
}
