/*
 * This module has been generated by smidump 0.4.8:
 *
 *      smidump -f yang RSTP-MIB
 *
 *  Modify to make easier for REST API
 */

module RSTP-MIB {

  /*** NAMESPACE / PREFIX DEFINITION ***/

  namespace "urn:ietf:params:xml:ns:yang:smiv2:RSTP-MIB";
  prefix "rstp-mib";

  /*** LINKAGE (IMPORTS / INCLUDES) ***/

  import BRIDGE-MIB { prefix "bridge-mib"; }
  import SNMPv2-TC  { prefix "smiv2"; }
  import ietf-yang-types { prefix yang; }
  

  /*** META INFORMATION ***/

  organization      
   "IETF Bridge MIB Working Group";

  contact           
   "Email: Bridge-mib@ietf.org";

  description       
   "The Bridge MIB Extension module for managing devices
    that support the Rapid Spanning Tree Protocol defined
    by IEEE 802.1w.
    
    Copyright (C) The Internet Society (2005).  This version of
    this MIB module is part of RFC 4318; See the RFC itself for
    full legal notices.";

  revision "2005-12-07" {
    description     
     "The initial version of this MIB module as published in
      RFC 4318.";
  }


  /* XXX table comments here XXX */

 grouping fsm-states {
	description
	   "This shall contain the previous and current state of the various state machines;
	    PIM: Port Information State Machine
	    PRTM: Port Role Transition State Machine
	    PRXM: Port Receive State Machine
	    PSTM: Port State Transition State Machine
	    TCM: Topology Change State Machine
	    PPM: Port Protocol Migration State Machine
	    PTXM: Port Transmit State Machine
	    PTIM: Port Timers State Machine
	    BDM: Bridge Detection State Machine";
		
	container states {
		description 
		   "Per port state machine states";
		
		leaf pim-prev-state {
			type string;
			config false;
			description
			  "PIM previous fsm state";
		}
		leaf pim-curr-state {
			type string;
			config false;			
			description
			  "PIM current fsm state";
		}
		leaf prtm-prev-state {
			type string;
			config false;			
			description
			  "PRTM previous fsm state";
		}
		leaf prtm-curr-state {
			type string;
			config false;			
			description
			  "PRTM current fsm state";
		}
		leaf prxm-prev-state {
			type string;
			config false;
			description
			  "PRXM previous fsm state";
		}
		leaf prxm-curr-state {
			type string;
			config false;			
			description
			  "PRXM current fsm state";
		}
		leaf pstm-prev-state {
			type string;
			config false;			
			description
			  "PSTM previous fsm state";
		}
		leaf pstm-curr-state {
			type string;
			config false;			
			description
			  "PSTM current fsm state";
		}
		leaf tcm-prev-state {
			type string;
			config false;			
			description
			  "TCM previous fsm state";
		}
		leaf tcm-curr-state {
			type string;
			config false;			
			description
			  "TCM current fsm state";
		}
		leaf ppm-prev-state {
			type string;
			config false;			
			description
			  "PPM previous fsm state";
		}
		leaf ppm-curr-state {
			type string;
			config false;			
			description
			  "PPM current fsm state";
		}
		leaf ptxm-prev-state {
			type string;
			config false;			
			description
			  "PTXM previous fsm state";
		}
		leaf ptxm-curr-state {
			type string;
			config false;			
			description
			  "PTXM current fsm state";
		}
		leaf ptim-prev-state {
			type string;
			config false;			
			description
			  "PTIM previous fsm state";
		}
		leaf ptim-curr-state {
			type string;
			config false;			
			description
			  "PTIM current fsm state";
		}
		leaf bdm-prev-state {
			type string;
			config false;			
			description
			  "BDM previous fsm state";
		}
		leaf bdm-curr-state {
			type string;
			config false;			
			description
			  "BDM current fsm state";
		}
	}
}

 grouping port-timers {
	description
	   "802.1d 17.17 State Machine Timers
		EdgeDelayWhile
	    FdWhile
	    HelloWhen
	    MdelayWhile
	    RbWhile
	    RcvdInfoWhile
	    RrWhile
	    TcWhile";
		
	container timers {
		description 
		   "Per Port Current Count of the various counters";
		
		leaf edge-delay-while {
			type int32;
			config false;
			description
			  "The Edge Delay timer. The time remaining, in the absence of a 
			received BPDU, before this port is identified as an operEdgePort.";
		}
		leaf fd-while {
			type int32;
			config false;
			description
			  "The Forward Delay timer. Used to delay Port State transitions 
			   until other Bridges have received spanning tree information";
		}
		leaf hello-when {
			type int32;
			config false;
			description
			  "The Hello timer. Used to ensure that at least one BPDU is 
			   transmitted by a Designated Port in each HelloTime period.";
		}
		leaf mdelay-while {
			type int32;
			config false;
			description
			  "The Migration Delay timer. Used by the Port Protocol 
			   Migration state machine to allow time for another RSTP Bridge 
			   on the same LAN to synchronize its migration state with this 
			   Port before the receipt of a BPDU can cause this Port to change 
			   the BPDU types it transmits. Initialized to MigrateTime (17.13.9).";
		}
		leaf rb-while {
			type int32;
			config false;
			description
			  "The Recent Backup timer. Maintained at its initial value, twice 
			   HelloTime, while the Port is a Backup Port.";
		}
		leaf rcvd-info-while {
			type int32;
			config false;
			description
			  "The Received Info timer. The time remaining before the spanning 
			   tree information received by this Port [portPriority (17.19.21) 
			   and portTimes (17.19.22)] is aged out if not refreshed by the 
			   receipt of a further Configuration Message.";
		}
		leaf rr-while {
			type int32;
			config false;
			description
			  "The Recent Root timer.";			
		}
		leaf tc-while {
			type int32;
			config false;
			description
			  "The Topology Change timer. TCN Messages are sent while this timer is running";			
		}
		leaf ba-while {
			type int32;
			config false;
			description
			  "Bridge Assurance timer, 3 * Hello Timer";
		}
	}
  }

  grouping port-statistics {
    description
      "BPDU packet statistics for the bridge interfaces";

    container counters {
      description
        "BPDU protocol counters";

	    leaf stp-in-pkts {
	        type yang:counter64;
			config false;			
	        description
	          "Number of STP PDUs received";
	      }

		leaf stp-out-pkts {
	        type yang:counter64;
			config false;			
	        description
	          "Number of STP BPDUs transmitted";
	      }
		
		leaf rstp-in-pkts {
	        type yang:counter64;
			config false;			
	        description
	          "Number of RSTP BPDUs received";
	      }
		leaf rstp-out-pkts {
	        type yang:counter64;
			config false;			
	        description
	          "Number of STP BPDUs transmitted";
	      }
		leaf tc-in-pkts {
	        type yang:counter64;
			config false;			
	        description
	          "Number of TC BPDUs received";
	      }
		leaf tc-out-pkts {
	        type yang:counter64;
			config false;			
	        description
	          "Number of TC BPDUs transmitted";
	      }
		leaf tcAck-in-pkts {
	        type yang:counter64;
			config false;			
	        description
	          "Number of TC Ack BPDUs received";
	      }
		leaf tcAck-out-pkts {
	        type yang:counter64;
			config false;			
	        description
	          "Number of TC Ack BPDUs transmitted";
	      }
		leaf pvst-in-pkts {
	        type yang:counter64;
			config false;			
	        description
	          "Number of PVST BPDUs received";
	      }
		leaf pvst-out-pkts {
	        type yang:counter64;
			config false;			
	        description
	          "Number of PVST BPDUs transmitted";
	      }
		leaf bpdu-in-pkts {
	        type yang:counter64;
			config false;			
	        description
	          "Number of BPDUs received";
	      }
		leaf bpdu-out-pkts {
	        type yang:counter64;
			config false;			
	        description
	          "Number of BPDUs transmitted";
	      }

	}
  }

  augment "/bridge-mib:Stp/bridge-mib:Port" {
    description     
     "A list of Rapid Spanning Tree information maintained by
      each port.";

    leaf ProtocolMigration {
      type smiv2:TruthValue;
      config true;
      description   
       "When operating in RSTP (version 2) mode, writing true(1)
        to this object forces this port to transmit RSTP BPDUs.
        Any other operation on this object has no effect and
        it always returns false(2) when read.";
      reference     
       "IEEE 802.1w clause 14.8.2.4, 17.18.10, 17.26";
    }
    leaf AdminPointToPoint {
      type enumeration {
        enum forceTrue  { value 0; }
        enum forceFalse { value 1; }
        enum auto       { value 2; }
      }
      config true;
      description   
       "The administrative point-to-point status of the LAN segment
        attached to this port, using the enumeration values of the
        IEEE 802.1w clause.  A value of forceTrue(0) indicates
        that this port should always be treated as if it is
        connected to a point-to-point link.  A value of
        forceFalse(1) indicates that this port should be treated as
        having a shared media connection.  A value of auto(2)
        indicates that this port is considered to have a
        point-to-point link if it is an Aggregator and all of its
        
        
        
        members are aggregatable, or if the MAC entity
        is configured for full duplex operation, either through
        auto-negotiation or by management means.  Manipulating this
        object changes the underlying adminPortToPortMAC.
        
        The value of this object MUST be retained across
        reinitializations of the management system.";
      reference     
       "IEEE 802.1w clause 6.4.3, 6.5, 14.8.2";
    }

    leaf AdminEdgePort {
      type smiv2:TruthValue;
      config true;
      description   
       "The administrative value of the Edge Port parameter.  A
        value of true(1) indicates that this port should be
        assumed as an edge-port, and a value of false(2) indicates
        that this port should be assumed as a non-edge-port.
        
        
        
        Setting this object will also cause the corresponding
        instance of OperEdgePort to change to the
        same value.  Note that even when this object's value
        is true, the value of the corresponding instance of
        OperEdgePort can be false if a BPDU has
        been received.
        
        The value of this object MUST be retained across
        reinitializations of the management system.";
      reference     
       "IEEE 802.1t clause 14.8.2, 18.3.3";
    }
	leaf AdminPathCost {
      type int32 {
        range "0..200000000";
      }
      config true;
      description   
       "The administratively assigned value for the contribution
        of this port to the path cost of paths toward the spanning
        tree root.
        
        Writing a value of '0' assigns the automatically calculated
        default Path Cost value to the port.  If the default Path
        Cost is being used, this object returns '0' when read.
        
        This complements the object PathCost or
        PathCost32, which returns the operational value
        of the path cost.
        
        
        
        The value of this object MUST be retained across
        reinitializations of the management system.";
      reference     
       "IEEE 802.1D-1998: Section 8.5.5.3";
    }
	leaf BpduGuard {
		type smiv2:TruthValue;
		config true;
		description
		"A Port as OperEdge which receives BPDU with BpduGuard enabled
		 will shut the port down.";
	}
	leaf BpduGuardInterval {
	type int32;
      config true;	
      units "seconds";
      description   
       "The interval time to which a port will try to recover from BPDU Guard err-disable
	   state.  If no BPDU frames are detected after this timeout plus 3 Times Hello
	   Time then the port will transition back to Up state.  If condition is cleared
	   manually then this operation is ignored.  If set to zero then timer is inactive
	   and recovery is based on manual intervention.";
	}
	
	leaf BridgeAssurance {
		 type smiv2:TruthValue;
		config true;
		description
		"When enabled BPDUs will be transmitted out of all stp ports regardless
		of state.  When an stp port fails to receive a BPDU the port should 
		transition to a Blocked state.  Upon reception of BDPU after shutdown 
		should transition port into the bridge.";
	}
  }
  augment "/bridge-mib:Stp/bridge-mib:PortState" {
    description     
     "A list of Rapid Spanning Tree information maintained by
      each port.";

     leaf AdminEdgePort {
      type smiv2:TruthValue;
      config false;
      description
       "The administrative value of the Edge Port parameter.  A
        value of true(1) indicates that this port should be
        assumed as an edge-port, and a value of false(2) indicates
        that this port should be assumed as a non-edge-port.



        Setting this object will also cause the corresponding
        instance of OperEdgePort to change to the
        same value.  Note that even when this object's value
        is true, the value of the corresponding instance of
        OperEdgePort can be false if a BPDU has
        been received.

        The value of this object MUST be retained across
        reinitializations of the management system.";
      reference
       "IEEE 802.1t clause 14.8.2, 18.3.3";
    }
	leaf AdminPathCost {
      type int32 {
        range "0..200000000";
      }
      config false;
      description
       "The administratively assigned value for the contribution
        of this port to the path cost of paths toward the spanning
        tree root.

        Writing a value of '0' assigns the automatically calculated
        default Path Cost value to the port.  If the default Path
        Cost is being used, this object returns '0' when read.

        This complements the object PathCost or
        PathCost32, which returns the operational value
        of the path cost.



        The value of this object MUST be retained across
        reinitializations of the management system.";
      reference
       "IEEE 802.1D-1998: Section 8.5.5.3";
    }

    leaf OperEdgePort {
      type smiv2:TruthValue;
      config false;
      description   
       "The operational value of the Edge Port parameter.  The
        object is initialized to the value of the corresponding
        instance of AdminEdgePort.  When the
        corresponding instance of AdminEdgePort is
        set, this object will be changed as well.  This object
        will also be changed to false on reception of a BPDU.";
      reference     
       "IEEE 802.1t clause 14.8.2, 18.3.4";
    }

    
    leaf OperPointToPoint {
      type smiv2:TruthValue;
      config false;
      description   
       "The operational point-to-point status of the LAN segment
        attached to this port.  It indicates whether a port is
        considered to have a point-to-point connection.
        If adminPointToPointMAC is set to auto(2), then the value
        of operPointToPointMAC is determined in accordance with the
        specific procedures defined for the MAC entity concerned,
        as defined in IEEE 802.1w, clause 6.5.  The value is
        determined dynamically; that is, it is re-evaluated whenever
        the value of adminPointToPointMAC changes, and whenever
        the specific procedures defined for the MAC entity evaluate
        a change in its point-to-point status.";
      reference     
       "IEEE 802.1w clause 6.4.3, 6.5, 14.8.2";
    }
	
	leaf MaxAge {
      type int32;
	  config false;	
      units "centi-seconds";
      description   
       "The value that all bridges use for MaxAge as advertised by
	   the root bridge.  Note that 802.1D-1998
        specifies that the range for this parameter is related
        to the value of BridgeHelloTime.  The
        granularity of this timer is specified by 802.1D-1998 to
        be 1 second.  An agent may return a badValue error if a
        set is attempted to a value that is not a whole number
        of seconds.";
      reference     
       "IEEE 802.1D-1998: clause 8.5.3.8";
    }

    leaf HelloTime {
      type int32;
      config false;	
      units "centi-seconds";
      description   
       "The value that all bridges use for HelloTime as advertised by
	   the root bridge.  The granularity of this
        timer is specified by 802.1D-1998 to be 1 second.  An
        agent may return a badValue error if a set is attempted
        
        
        
        to a value that is not a whole number of seconds.";
      reference     
       "IEEE 802.1D-1998: clause 8.5.3.9";
    }

    leaf ForwardDelay {
      type int32 ;
	  config false;	
      units "centi-seconds";
      description   
       "The value that all bridges use for ForwardDelay as advertised by
	   the root bridge.  Note that
        802.1D-1998 specifies that the range for this parameter
        is related to the value of dot1dStpBridgeMaxAge.  The
        granularity of this timer is specified by 802.1D-1998 to
        be 1 second.  An agent may return a badValue error if a
        set is attempted to a value that is not a whole number
        of seconds.";
      reference     
       "IEEE 802.1D-1998: clause 8.5.3.10";
    }
	
	leaf BridgeAssurance {
		type smiv2:TruthValue;
		config false;
		description
		 "Used to make sure that a neighboring switch does not malfunction 
		and begin forwarding frames when it should not.  It does this by
		monitoring receipt of BPDUs on point-to-point links.  When the 
		BPDUs stop being received, the port is put into blocking state 
		(actually a port inconsistent state, which stops forwarding).  
		When BPDUs restart, the port resumes normal RSTP or MST modes.  
		This handles unidirectional links as well as the malfunction of a 
		neighboring switch where STP stops sending BPDUs but the switch 
		continues to forward frames. ";
	}
	leaf BridgeAssuranceInconsistant {
		type smiv2:TruthValue;
		config false;
		description
		 "When port stops receiving BPDU on a Bridge Assurance enabled
		port then this will be set.";
	}
	
	leaf BpduGuard {
		type smiv2:TruthValue;
		config false;
		description
		 "Used in conjuction with AdminEdge to shutdown a port when a BPDU
		is received.  Protects against loops in the network";
	}
	leaf BpduGuardInterval {
	type int32;
      config false;	
      units "seconds";
      description   
       "The interval time to which a port will try to recover from BPDU Guard err-disable
	   state.  If no BPDU frames are detected after this timeout plus 3 Times Hello
	   Time then the port will transition back to Up state.  If condition is cleared
	   manually then this operation is ignored.  If set to zero then timer is inactive
	   and recovery is based on manual intervention.";
	}
	
	leaf BpduGuardDetected {
	  type smiv2:TruthValue;
	  config false;	
      description
	   "Indicates whether a BPDU frame was received on this STP port if the port 
	    is and Edge Port and BPDU Guard is enabled";
	}
	leaf stp-in-pkts {
	        type yang:counter64;
			config false;
	        description
	          "Number of STP PDUs received";
	      }

		leaf stp-out-pkts {
	        type yang:counter64;
			config false;
	        description
	          "Number of STP BPDUs transmitted";
	      }

		leaf rstp-in-pkts {
	        type yang:counter64;
			config false;
	        description
	          "Number of RSTP BPDUs received";
	      }
		leaf rstp-out-pkts {
	        type yang:counter64;
			config false;
	        description
	          "Number of RSTP BPDUs transmitted";
	      }
		leaf tc-in-pkts {
	        type yang:counter64;
			config false;
	        description
	          "Number of TC BPDUs received";
	      }
		leaf tc-out-pkts {
	        type yang:counter64;
			config false;
	        description
	          "Number of TC BPDUs transmitted";
	      }
		leaf tcAck-in-pkts {
	        type yang:counter64;
			config false;
	        description
	          "Number of TC Ack BPDUs received";
	      }
		leaf tcAck-out-pkts {
	        type yang:counter64;
			config false;
	        description
	          "Number of TC Ack BPDUs transmitted";
	      }
		leaf pvst-in-pkts {
	        type yang:counter64;
			config false;
	        description
	          "Number of PVST BPDUs received";
	      }
		leaf pvst-out-pkts {
	        type yang:counter64;
			config false;
	        description
	          "Number of PVST BPDUs transmitted";
	      }
		leaf bpdu-in-pkts {
	        type yang:counter64;
			config false;
	        description
	          "Number of BPDUs received";
	      }
		leaf bpdu-out-pkts {
	        type yang:counter64;
			config false;
	        description
	          "Number of BPDUs transmitted";
	      }
		leaf pim-prev-state {
			type string;
			config false;
			description
			  "PIM previous fsm state";
		}
		leaf pim-curr-state {
			type string;
			config false;
			description
			  "PIM current fsm state";
		}
		leaf prtm-prev-state {
			type string;
			config false;
			description
			  "PRTM previous fsm state";
		}
		leaf prtm-curr-state {
			type string;
			config false;
			description
			  "PRTM current fsm state";
		}
		leaf prxm-prev-state {
			type string;
			config false;
			description
			  "PRXM previous fsm state";
		}
		leaf prxm-curr-state {
			type string;
			config false;
			description
			  "PRXM current fsm state";
		}
		leaf pstm-prev-state {
			type string;
			config false;
			description
			  "PSTM previous fsm state";
		}
		leaf pstm-curr-state {
			type string;
			config false;
			description
			  "PSTM current fsm state";
		}
		leaf tcm-prev-state {
			type string;
			config false;
			description
			  "TCM previous fsm state";
		}
		leaf tcm-curr-state {
			type string;
			config false;
			description
			  "TCM current fsm state";
		}
		leaf ppm-prev-state {
			type string;
			config false;
			description
			  "PPM previous fsm state";
		}
		leaf ppm-curr-state {
			type string;
			config false;
			description
			  "PPM current fsm state";
		}
		leaf ptxm-prev-state {
			type string;
			config false;
			description
			  "PTXM previous fsm state";
		}
		leaf ptxm-curr-state {
			type string;
			config false;
			description
			  "PTXM current fsm state";
		}
		leaf ptim-prev-state {
			type string;
			config false;
			description
			  "PTIM previous fsm state";
		}
		leaf ptim-curr-state {
			type string;
			config false;
			description
			  "PTIM current fsm state";
		}
		leaf bdm-prev-state {
			type string;
			config false;
			description
			  "BDM previous fsm state";
		}
		leaf bdm-curr-state {
			type string;
			config false;
			description
			  "BDM current fsm state";
		}
		leaf edge-delay-while {
			type int32;
			config false;
			description
			  "The Edge Delay timer. The time remaining, in the absence of a
			received BPDU, before this port is identified as an operEdgePort.";
		}
		leaf fd-while {
			type int32;
			config false;
			description
			  "The Forward Delay timer. Used to delay Port State transitions
			   until other Bridges have received spanning tree information";
		}
		leaf hello-when {
			type int32;
			config false;
			description
			  "The Hello timer. Used to ensure that at least one BPDU is
			   transmitted by a Designated Port in each HelloTime period.";
		}
		leaf mdelay-while {
			type int32;
			config false;
			description
			  "The Migration Delay timer. Used by the Port Protocol
			   Migration state machine to allow time for another RSTP Bridge
			   on the same LAN to synchronize its migration state with this
			   Port before the receipt of a BPDU can cause this Port to change
			   the BPDU types it transmits. Initialized to MigrateTime (17.13.9).";
		}
		leaf rb-while {
			type int32;
			config false;
			description
			  "The Recent Backup timer. Maintained at its initial value, twice
			   HelloTime, while the Port is a Backup Port.";
		}
		leaf rcvd-info-while {
			type int32;
			config false;
			description
			  "The Received Info timer. The time remaining before the spanning
			   tree information received by this Port [portPriority (17.19.21)
			   and portTimes (17.19.22)] is aged out if not refreshed by the
			   receipt of a further Configuration Message.";
		}
		leaf rr-while {
			type int32;
			config false;
			description
			  "The Recent Root timer.";
		}
		leaf tc-while {
			type int32;
			config false;
			description
			  "The Topology Change timer. TCN Messages are sent while this timer is running";
		}
		leaf ba-while {
			type int32;
			config false;
			description
			  "Bridge Assurance timer, 3 * Hello Timer";
		}
  }

} /* end of module RSTP-MIB */
