module PVST {

  /*** NAMESPACE / PREFIX DEFINITION ***/

  namespace "urn:ietf:params:xml:ns:yang:smiv2:PVST";
  prefix "pvst";

  /*** LINKAGE (IMPORTS / INCLUDES) ***/

  import BRIDGE-MIB { prefix "bridge-mib"; }

  /*** META INFORMATION ***/

  organization      
   "IETF Bridge MIB Working Group";

  contact           
   "Email: Bridge-mib@ietf.org";

  description       
   "The Bridge MIB Extension module for managing devices
    that support the Rapid Spanning Tree Protocol defined
    by IEEE 802.1w.
    
    Copyright (C) The Internet Society (2005).  This version of
    this MIB module is part of RFC 4318; See the RFC itself for
    full legal notices.";

  revision "2005-12-07" {
    description     
     "The initial version of this MIB module as published in
      RFC 4318.";
  }


  /* XXX table comments here XXX */

  augment "/bridge-mib:dot1dStpBridge/bridge-mib:Config" {
    description     
     "A list of Rapid Per Vlan Spanning Tree information maintained by
      each bridge.";

    leaf dot1dStpVlan {
      type uint16;
      config true;
      description   
       "Each bridge is associated with a domain.  Typically this domain
	   is represented as the vlan";
      reference     
       "Cisco PVST+";
    }
  }
  augment "/bridge-mib:dot1dStpBridge/bridge-mib:State" {
    description     
     "A list of Rapid Per Vlan Spanning Tree information maintained by
      each bridge.";

    leaf dot1dStpVlan {
      type uint16;
      config false;
      description   
       "Each bridge is associated with a domain.  Typically this domain
	   is represented as the vlan";
      reference     
       "Cisco PVST+";
    }
  }

} /* end of module PVST */
